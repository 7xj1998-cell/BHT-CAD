;;; BHT modular loader; Application Bundle / APPLOAD entry point.
(vl-load-com)
(setq *bht-version* "0.6.12")
(setq *bht-lsp-file* (findfile "BHT-0.6.12.lsp"))
(if (and (not *bht-module-root*) *bht-lsp-file*) (setq *bht-module-root* (vl-filename-directory *bht-lsp-file*)))
(if (and (not *bht-module-root*) (member (type BHTRUNTIMEROOT) '(SUBR USUBR EXRXSUBR))) (setq *bht-module-root* (BHTRUNTIMEROOT)))
(defun bht:load-modules (root / name result)
  (if (not root) (progn (princ "\nBHT: chưa tìm thấy thư mục module. APPLOAD từ thư mục Support hoặc đặt *bht-module-root* trước khi load.") (exit)))
  (foreach name '("01-foundation" "02-points" "03-labels" "04-objects" "05-photos" "06-routes" "07-segments" "08-signs" "09-draworder" "10-reports" "11-diagnostics" "12-api")
    (setq result (load (strcat root "/modules/" name ".lsp")))
    ))
(bht:load-modules *bht-module-root*)
(princ)
