(setq m649-fails 0)
(defun m649-check (n ok) (if (not ok) (setq m649-fails (1+ m649-fails))) (princ (strcat "\n" (if ok "PASS M649 " "FAIL M649 ") n)))
(defun m649-point (id x y / e)
  (setq e (entmakex (list '(0 . "POINT") (cons 10 (list x y 0.0)))))
  (bht:pt-write-xdata e id "QA" id id x y 0.0 "" "" "" "") e)
(setq p0 (m649-point "M0" 0.0 2.0) p1 (m649-point "M1" 1000.0 2.0) pm (m649-point "MID" 500.0 3.0)
      before0 (entget p0 '("BHT_PT")) before1 (entget p1 '("BHT_PT")))
(bht:obj-create "KM0" '(("nhom" . "COT_KM") ("marker_km" . "49")) '("M0") T)
(bht:obj-create "KM1" '(("nhom" . "COT_KM") ("marker_km" . "50")) '("M1") T)
(bht:obj-create "MID" '(("nhom" . "BIEN_BAO")) '("MID") T)
(m649-check "own-station-without-route" (and (= (bht:get (bht:obj-read "KM0") "ly_trinh_m") "49000.000") (not (eq (car (bht:station-one "KM0")) 'LOI))))
(setq pl (entmakex '((0 . "LWPOLYLINE") (100 . "AcDbEntity") (100 . "AcDbPolyline") (90 . 2) (70 . 0) (10 0.0 0.0) (10 1000.0 0.0))))
(bht:route-create "TEST" pl "TIM_DUONG" 20.0 0.0 nil "QA")
(setq rr (bht:route-read "TEST"))
(m649-check "two-entered-Km-used-without-confirmation" (equal (cdr (assoc 'station (bht:station '(500.0 3.0 0.0)))) 49500.0 1e-6))
(m649-check "no-persisted-copy" (null (bht:route-marks rr)))
(bht:station-one "MID")
(m649-check "single-object-save-result" (= (bht:get (bht:obj-read "MID") "ly_trinh_m") "49500.000"))
(bht:station-objects)
(m649-check "batch-keeps-manual-marker" (and (= (bht:get (bht:obj-read "KM0") "nguon_km") "Số Km/H đã nhập") (= (bht:get (bht:obj-read "MID") "ly_trinh_m") "49500.000")))
(bht:obj-write "KM1" (bht:set (bht:obj-read "KM1") "marker_km" "51"))
(m649-check "edit-immediately-changes-controls" (equal (cdr (assoc 'station (bht:station '(500.0 3.0 0.0)))) 50000.0 1e-6))
(bht:obj-write "KM1" (bht:set (bht:obj-read "KM1") "marker_km" "50"))
(bht:obj-create "H" '(("nhom" . "COC_TIEU") ("marker_km" . "49") ("marker_h" . "5")) '("MID") T)
(m649-check "hectometre-used" (= (length (car (bht:route-controls rr))) 3))
(bht:obj-create "DUP" '(("nhom" . "COT_KM") ("marker_km" . "49")) '("M0") T)
(m649-check "same-position-same-value-deduplicated" (and (= (length (car (bht:route-controls rr))) 3) (null (cadr (bht:route-controls rr)))))
(bht:obj-write "DUP" (bht:set (bht:obj-read "DUP") "marker_km" "52"))
(m649-check "conflicting-value-blocks" (= (cdr (assoc 'status (bht:station '(250.0 0.0 0.0)))) "MAU_THUAN_MOC"))
(bht:obj-delete "DUP")
(m649-check "deletion-removes-conflict" (bht:station-determined (cdr (assoc 'status (bht:station '(250.0 0.0 0.0))))))
(bht:obj-write "H" (bht:set (bht:obj-read "H") "marker_h" ""))
(m649-check "incomplete-H-not-used" (= (length (car (bht:route-controls rr))) 2))
(bht:route-add-mark "TEST" 0.0 49000.0 49000.0 "MANUAL" "")
(m649-check "matching-manual-control-preserved" (and (= (length (car (bht:route-controls (bht:route-read "TEST")))) 2) (= (length (bht:route-marks (bht:route-read "TEST"))) 1)))
(bht:route-del-mark "TEST" 0)
(setq pl2 (entmakex '((0 . "LWPOLYLINE") (100 . "AcDbEntity") (100 . "AcDbPolyline") (90 . 2) (70 . 0) (10 0.0 5.0) (10 1000.0 5.0))))
(bht:route-create "OTHER" pl2 "TIM_DUONG" 20.0 0.0 nil "QA")
(setq cc (bht:route-controls rr))
(m649-check "ambiguous-routes-not-guessed" (and (null (car cc)) (= (length (caddr cc)) 2)))
(bht:route-delete "OTHER")
(bht:route-set-start-dir "TEST" '(1000.0 0.0 0.0) -1)
(m649-check "reverse-route-reprojects-controls" (equal (cdr (assoc 'station (bht:station '(250.0 0.0 0.0)))) 49250.0 1e-6))
(bht:obj-delete "KM1")
(m649-check "deleted-marker-not-cached" (= (length (car (bht:route-controls (bht:route-read "TEST")))) 1))
(m649-check "survey-unchanged" (and (equal before0 (entget p0 '("BHT_PT"))) (equal before1 (entget p1 '("BHT_PT")))))
(princ (strcat "\nM649-FAIL=" (itoa m649-fails)))
