(defun upgrade-transform (e)
  (vl-remove-if-not '(lambda (p) (member (car p) '(10 41 42 43 50))) (entget e)))
(defun upgrade-outline-p (id / e name)
  (setq e (cdr (assoc id (bht:tagged-pairs "INSERT" "BHT_KH" 1))))
  (and e (setq name (cdr (assoc 2 (entget e)))) (wcmatch name "*_NOFILL_V0633") (= (BHTTESTVISIBLEBACKGROUNDS name) 0)))
(setq upgrade-pairs nil)
(foreach group '("BIEN_BAO" "BANG_CHI_DAN" "BANG_QC" "KHAC" "CHUA_XAC_DINH")
  (setq id (strcat "OBJ-UP-" group))
  (bht:obj-create id (list (cons "nhom" group) '("ma_hieu" . "R.415a") '("mo_ta" . "Tên trên biển")) '("SIGN-PT") T)
  (bht:kh-free-apply id '(210.0 80.0 0.0) 0.3 nil)
  (setq upgrade-pairs (cons id upgrade-pairs)))
(signs-check "fill-off-all-five-groups-api" (= (car (bht:api-sign-fill "0")) "OK"))
(foreach id upgrade-pairs (signs-check (strcat "fill-off-no-fill-" id) (upgrade-outline-p id)))
(bht:api-sign-fill "1")
(foreach id upgrade-pairs
  (setq e (cdr (assoc id (bht:tagged-pairs "INSERT" "BHT_KH" 1))))
  (signs-check (strcat "fill-on-restored-" id) (if (= id "OBJ-UP-BANG_CHI_DAN") (= (BHTTESTVISIBLEFILLS (cdr (assoc 2 (entget e)))) 0) (> (BHTTESTVISIBLEFILLS (cdr (assoc 2 (entget e)))) 0))))
(bht:api-sign-fill "0")
(setq upgrade-manual (cdr (assoc "OBJ-UP-BIEN_BAO" (bht:tagged-pairs "INSERT" "BHT_KH" 1))))
(bht:block "BHT_TDT_V0627_R_415A" (list (bht:line-g '(0.0 0.0 0.0) '(1.0 1.0 0.0))))
(entmod (bht:dxf-put (bht:dxf-put (bht:dxf-put (bht:dxf-put (entget upgrade-manual) 2 "BHT_TDT_V0627_R_415A") 41 1.3) 42 0.8) 43 1.2))
(bht:obj-create "OBJ-UP-AUTO" '(("nhom" . "BIEN_BAO") ("ma_hieu" . "R.415b")) '("SIGN-PT") T)
(bht:symbol-sync '("OBJ-UP-AUTO"))
(setq upgrade-auto (cdr (assoc "OBJ-UP-AUTO" (bht:tagged-pairs "INSERT" "BHT_KH" 1))))
(entmod (bht:dxf-put (entget upgrade-auto) 2 "BHT_TDT_V0627_R_415A"))
(bht:obj-create "OBJ-UP-NOSYMBOL" '(("nhom" . "BIEN_BAO") ("ma_hieu" . "R.415a")) '("SIGN-PT") T)
(setq upgrade-transform-before (list (upgrade-transform upgrade-manual) (upgrade-transform upgrade-auto))
  upgrade-xdata-before (list (assoc -3 (entget upgrade-manual '("BHT_KH"))) (assoc -3 (entget upgrade-auto '("BHT_KH"))))
  upgrade-RTK-before (entget survey '("BHT_PT"))
  upgrade-records-before (mapcar '(lambda (id) (cons id (bht:obj-read id))) (bht:obj-ids)))
(bht:meta-set "symbol_build" "0.6.27")
(princ "\nUPGRADE-FIXTURE-READY")
