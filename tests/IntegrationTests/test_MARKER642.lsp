(setq marker-fail 0)
(defun marker-check (n ok) (if (not ok) (setq marker-fail (1+ marker-fail))) (princ (strcat "\n" (if ok "PASS MARKER " "FAIL MARKER ") n)))
(bht:obj-create "MARKER642" '(("nhom" . "COC_TIEU") ("marker_km" . "40") ("marker_h" . "4")) '("HEAD-1") T)
(foreach a '(0.0 0.7 2.7 4.8)
 (bht:kh-free-apply "MARKER642" '(5.0 -4.0 0.0) a nil)
 (setq md (entget (cdr (assoc "MARKER642" (bht:tagged-pairs "INSERT" "BHT_KH" 1))))
       mt (entget (cdr (assoc "MARKER642" (bht:tagged-pairs "TEXT" "BHT_KH" 1))))
       ms (abs (cdr (assoc 41 md))))
 (marker-check "content-H4/40" (= (cdr (assoc 1 mt)) "H4/40"))
 (marker-check "compact-height" (equal (cdr (assoc 40 mt)) (* 0.22 ms) 1e-6))
 (marker-check "follows-symbol-exact-angle" (heading-same-angle (cdr (assoc 50 mt)) a))
 (marker-check "local-offset" (equal (cdr (assoc 11 mt)) (polar (polar (cdr (assoc 10 md)) a (* -0.78 ms)) (+ a (/ pi 2)) (* -0.3944 ms)) 1e-6)))
(setq marker-insert (cdr (assoc "MARKER642" (bht:tagged-pairs "INSERT" "BHT_KH" 1))))
(entmod (bht:dxf-put (entget marker-insert) 50 1.2))
(bht:symbol-sync '("MARKER642"))
(setq mt (entget (cdr (assoc "MARKER642" (bht:tagged-pairs "TEXT" "BHT_KH" 1)))))
(marker-check "manual-CAD-rotation-label-follows" (heading-same-angle (cdr (assoc 50 mt)) 1.2))
(setq marker-stable mt)
(bht:symbol-sync '("MARKER642"))
(marker-check "repeat-label-idempotent" (equal marker-stable (entget (cdr (assoc "MARKER642" (bht:tagged-pairs "TEXT" "BHT_KH" 1))))))
(marker-check "survey-unchanged" (equal heading-rtk (list (entget heading-p1 '("BHT_PT")) (entget heading-p2 '("BHT_PT")))))
(princ (strcat "\nMARKER-FAIL=" (itoa marker-fail)))
