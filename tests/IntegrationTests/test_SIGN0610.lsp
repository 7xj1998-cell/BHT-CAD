(setq *sign0610-fail* 0)
(bht:meta-set "kh_block_cot_km" "")
(bht:meta-set "kh_block_bien_bao" "")
(bht:meta-set "sign_fill_all" "1")
(defun sign0610-check (name ok) (princ (strcat "\n" (if ok "PASS " "FAIL ") name)) (if (not ok) (setq *sign0610-fail* (1+ *sign0610-fail*))))
(setq qa0610-point (entmakex '((0 . "POINT") (8 . "BHT_RTK") (10 100000.0 99996.0 0.0))))
(bht:pt-write-xdata qa0610-point "QA0610-PT" "QA0610" "1" "Cọc thử" 99996.0 100000.0 0.0 "COC_TIEU" "test" "coctiu.H9-39" "")
(bht:obj-create "OBJ-QA0610-H" '(("nhom" . "COC_TIEU") ("marker_km" . "39") ("marker_h" . "9")) '("QA0610-PT") T)
(setq qa0610-h (bht:obj-read "OBJ-QA0610-H"))
(sign0610-check "hectometre-fields-persisted" (and (= (bht:get qa0610-h "marker_km") "39") (= (bht:get qa0610-h "marker_h") "9")))
(sign0610-check "hectometre-H9-39" (= (bht:kh-label "OBJ-QA0610-H" qa0610-h) "H9/39"))
(bht:kh-free-apply "OBJ-QA0610-H" '(100000.0 99996.0 0.0) (- (/ pi 2)) nil)
(bht:symbol-sync '("OBJ-QA0610-H"))
(setq qa0610-htext (cdr (assoc "OBJ-QA0610-H" (bht:tagged-pairs "TEXT" "BHT_KH" 1))))
(sign0610-check "hectometre-rendered-H9-39" (= (cdr (assoc 1 (entget qa0610-htext))) "H9/39"))
(sign0610-check "hectometre-horizontal-label" (equal (cdr (assoc 50 (entget qa0610-htext))) 0.0 1e-8))
(bht:obj-create "OBJ-QA0610-KM" '(("nhom" . "COT_KM") ("marker_km" . "39")) '("QA0610-PT") T)
(setq qa0610-km (bht:obj-read "OBJ-QA0610-KM"))
(princ (list "KM-BLOCK" (bht:kh-block qa0610-km) "FUNCTION" (bht:fn-defined-p 'BHTMILESTONE)))
(sign0610-check "milestone-fields-persisted" (= (bht:get qa0610-km "marker_km") "39"))
(sign0610-check "milestone-parameterized-block" (= (bht:kh-block qa0610-km) "BHT_KH_COT_KM_V0611_39"))
(bht:obj-create "OBJ-QA0610-BRIDGE" '(("nhom" . "BIEN_BAO") ("ma_hieu" . "I.439") ("bridge_name" . "CẦU YÊN CHÂU") ("sign_chainage" . "Km252+831") ("road_name" . "QL.6")) '("QA0610-PT") T)
(setq qa0610-bridge (bht:obj-read "OBJ-QA0610-BRIDGE"))
(princ (list "BRIDGE-BLOCK" (bht:kh-block qa0610-bridge) "FUNCTION" (bht:fn-defined-p 'BHTBRIDGESIGN)))
(sign0610-check "bridge-fields-persisted" (and (= (bht:get qa0610-bridge "bridge_name") "CẦU YÊN CHÂU") (= (bht:get qa0610-bridge "road_name") "QL.6")))
(sign0610-check "bridge-renderer-used" (wcmatch (bht:kh-block qa0610-bridge) "BHT_I439_V0611_*"))
(setq qa0610-before (bht:obj-read "OBJ-QA0610-H") qa0610-before-entity (entget qa0610-htext))
(bht:symbol-sync '("OBJ-QA0610-H"))
(sign0610-check "hectometre-repeat-idempotent" (and (equal qa0610-before (bht:obj-read "OBJ-QA0610-H")) (equal qa0610-before-entity (entget qa0610-htext))))
(sign0610-check "original-survey-point-unchanged" (equal (cdr (assoc 10 (entget qa0610-point))) '(100000.0 99996.0 0.0)))
(princ (strcat "\nSIGN0610-FAIL=" (itoa *sign0610-fail*)))
(princ)
