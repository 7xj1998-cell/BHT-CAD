;;; BHT 0.3.3 - phien A: ban ve moi (BAN SAO sample-route.dwg). Nhan tu dong / tay,
;;; ho so doi tuong, ky hieu theo ID, thu tu hien thi, anh, nhap trung dinh dang.
(load (strcat (getenv "BHT_TEST_DIR") "/t_common.lsp"))
(tbegin "A")
(setq *D* (strcat *T-DIR* "data/"))
(setq *CSV* (strcat *D* "survey.csv"))
(setq *PH* (strcat (getenv "BHT_LEGACY_TEST_DIR") "/anh/kmz_out/BHT_PHOTO.tsv"))
(setq *MOVED* (strcat *T-DIR* "anh_da_doi/kmz_out"))
(setq e (tload))
(tchk "T00" "nạp BHT-5.0" (and (null e) (= *bht-version* "0.6.55")) (if e e *bht-version*))
(setq *bht-no-launch* T)

;; ---------- thuc the NGOAI BHT ----------
(bht:layer "BHT_RTK_TEN" 7) (bht:layer "BHT_NHAN" 2) (bht:layer "BHT_KYHIEU" 1) (bht:symbol-blocks) (regapp "APP_KHAC")
(setq F1 (entmakex '((0 . "TEXT") (8 . "BHT_RTK_TEN") (10 575100.0 1180100.0 0.0) (40 . 1.0) (1 . "KHONG PHAI NHAN BHT"))))
(setq F2 (entmakex '((0 . "TEXT") (8 . "BHT_NHAN") (10 575110.0 1180100.0 0.0) (40 . 1.0) (1 . "OBJ-T1")
                     (-3 ("APP_KHAC" (1000 . "OBJ-T1"))))))
(setq F3 (entmakex '((0 . "INSERT") (2 . "BHT_KH_COC_TIEU_V043") (8 . "BHT_KYHIEU") (10 575120.0 1180100.0 0.0))))
(setq SNAP (t-snapshot))
(tlog (strcat "   thực thể ngoài BHT chụp lại: " (itoa (length SNAP))))

;; ---------- R: nhap ----------
(setq r (tsafe "R01" "nhập CSV" '(lambda () (bht:import-csv *CSV* "BOT19"))))
(if r (tchk "R01" "nhập 526 điểm RTK (CSV trực tiếp = mặc định)" (and (= (rv r 'added) 526) (= (rv r 'invalid) 0)) r))
(setq v (t-verify-csv *CSV* "BOT19"))
(tchk "R02" "tọa độ + chuỗi gốc 526/526 không đổi (X=E, Y=N, Z)" (and (= (car v) 526) (= (cadr v) 0)) v)
(setq PTS0 (t-pt-coords))
;; D: TSV trao doi tao tu du lieu da nhap -> nhap lai bang TSV phai canh bao, khong them diem
(setq tsv (strcat *T-DIR* "run/BHT_RTK_trao_doi.tsv") f (open tsv "w" "utf8"))
(write-line "BHT_ID\tSRC_POINT\tNORTHING\tEASTING\tZ\tRAW_DESC\tSRC_ROW\tSOURCE_FILE" f)
(foreach it (bht:pt-all)
  (setq p (cdr it))
  (write-line (strcat (bht:pv p 'id) "\t" (bht:pv p 'name) "\t" (bht:pv p 'n) "\t" (bht:pv p 'e) "\t" (bht:pv p 'z) "\t"
                      (bht:pv p 'desc) "\t" (bht:pv p 'row) "\tsurvey.csv") f))
(close f)
(setq r (bht:import-tsv tsv) chk (bht:dual-import-check '("BOT19") "TSV" r) ds (bht:rec-read "DATASET" "BOT19"))
(tchk "D01" "nhập lại cùng dữ liệu bằng TSV: 0 điểm thêm, không trùng, cảnh báo 'không cần nhập cả CSV và TSV'; dataset ghi định dạng CSV+TSV"
      (and r (= (rv r 'added) 0) (= (length (bht:pt-all)) 526) chk (= (bht:get ds "dinh_dang") "CSV+TSV"))
      (list r (bht:get ds "dinh_dang")))

;; ---------- L: nhan ----------
(setq nmota 0)
(foreach rr (car (bht:csv-records *CSV* "BOT19")) (if (/= (nth 7 rr) "") (setq nmota (1+ nmota))))
(setq t0 (getvar "MILLISECS") r (tsafe "L01" "tạo nhãn" '(lambda () (bht:lbl-sync))) t1 (getvar "MILLISECS"))
(setq st (t-lbl-states))
(if r (tchk "L01" "tạo nhãn tự động cho 526 điểm (tên+mô tả+cao độ), không trùng, trạng thái TU_DONG"
            (and (= (rv r 'points) 526) (= (t-lbl-count "TEN") 526) (= (t-lbl-count "CAODO") 526) (= (t-lbl-count "MOTA") nmota)
                 (= (rv r 'created) (+ 526 526 nmota)) (= (t-lbl-dups) 0) (equal st (list (+ 526 526 nmota) 0 0)))
            (strcat (vl-princ-to-string r) " | trạng thái (tự động tay cũ)=" (vl-princ-to-string st) " | " (itoa (- t1 t0)) " ms")))
(setq v (t-verify-labels *CSV* "BOT19" '("TEN" "MOTA" "CAODO")))
(tchk "L02" "chữ nhãn = CSV nguyên văn" (and (null (cadr v)) (= (car v) (+ 526 526 nmota))) (list (car v) (cadr v)))
(setq OVA (bht:lbl-overlaps nil))
(tlog (strcat "   chồng lấn sau bố trí tự động (526 điểm thật): " (bht:lbl-overlap-text OVA)))
;; so voi vi tri mac dinh 0.3.2
(setq allp (mapcar 'car (bht:pt-all)))
(t-lbl-to-legacy allp)
(setq OVL (bht:lbl-overlaps nil) stl (t-lbl-states))
(setq t0 (getvar "MILLISECS") r (bht:lbl-reset allp) t1 (getvar "MILLISECS"))
(setq OVR (bht:lbl-overlaps nil) str (t-lbl-states))
(tchk "L03" "526 điểm thật: chồng lấn vị trí 0.3.2 (trước) -> sau BHTNHANTUDONG (trả về tự động + bố trí lại) giảm; không trùng nhãn"
      (and (< (cdr (assoc 'overlapped OVR)) (cdr (assoc 'overlapped OVL))) (= (t-lbl-dups) 0)
           (equal str (list (+ 526 526 nmota) 0 0)))
      (strcat "TRƯỚC (vị trí 0.3.2): " (bht:lbl-overlap-text OVL) " || SAU: " (bht:lbl-overlap-text OVR)
              " | " (itoa (- t1 t0)) " ms | trạng thái sau khi đặt về vị trí 0.3.2 " (vl-princ-to-string stl)))
;; L04 chay lai khong doi gi
(setq POS1 (t-lbl-positions) r (bht:lbl-sync) POS2 (t-lbl-positions))
(tchk "L04" "chạy lại BHTNHANDIEM: không tạo/xóa/dời nhãn nào" (and (= (rv r 'created) 0) (= (rv r 'deleted) 0) (= (rv r 'laidout) 0) (equal POS1 POS2)) r)
;; L05 doi tay
(setq M "BOT19-R-000100" me (t-lbl-ent M "TEN") p0 (cdr (assoc 10 (entget me))))
(t-move me 3.0 2.0)
(setq pm (list (+ (car p0) 3.0) (+ (cadr p0) 2.0)))
(setq r1 (bht:lbl-sync) s1 (bht:lbl-state (t-lbl-ent M "TEN")) q1 (t-lbl-pos M "TEN"))
(bht:meta-set "nhan_h" "1.2")
(setq r2 (bht:lbl-sync) q2 (t-lbl-pos M "TEN") h2 (cdr (assoc 40 (entget (t-lbl-ent M "TEN")))))
(setq r3 (bht:lbl-sync-scope 'ALL) q3 (t-lbl-pos M "TEN") s3 (bht:lbl-state (t-lbl-ent M "TEN")))
(bht:meta-set "nhan_h" "1.0") (bht:lbl-sync)
(setq q4 (t-lbl-pos M "TEN"))
(tchk "L05" "nhãn người dùng dời tay: nhận ra TAY, giữ nguyên vị trí khi cập nhật (đổi cao chữ, bố trí lại TẤT CẢ)"
      (and (eq s1 'TAY) (eq s3 'TAY) (bht:pt-near q1 pm 1e-6) (bht:pt-near q2 pm 1e-6) (bht:pt-near q3 pm 1e-6) (bht:pt-near q4 pm 1e-6)
           (equal h2 1.2 1e-9) (>= (rv r2 'manual) 1) (= (t-lbl-dups) 0))
      (list pm q1 q2 q3 q4 (rv r2 'manual)))
(setq r (bht:lbl-reset (list M)) s5 (bht:lbl-state (t-lbl-ent M "TEN")) q5 (t-lbl-pos M "TEN"))
(tchk "L06" "trả nhãn đã dời về tự động (BHTNHANTUDONG cho 1 điểm): trạng thái TU_DONG, rời vị trí tay"
      (and (eq s5 'AUTO) (not (bht:pt-near q5 pm 1e-6)) (= (car r) 1)) (list r q5))
;; L07 bo tri lai theo pham vi
(setq SC '("BOT19-R-000200" "BOT19-R-000201" "BOT19-R-000202" "BOT19-R-000203" "BOT19-R-000204"))
(setq POS1 (t-lbl-positions) r (bht:lbl-sync-scope SC) POS2 (t-lbl-positions) moved 0)
(foreach pp POS1 (if (and (not (member (car (bht:split (car pp) "|")) SC)) (not (equal (cdr pp) (cdr (assoc (car pp) POS2)) 1e-9)))
                   (setq moved (1+ moved))))
(tchk "L07" "bố trí lại chỉ trong phạm vi (5 ID): nhãn ngoài phạm vi không đổi vị trí" (and (= moved 0) (= (rv r 'laidout) 5)) (list (rv r 'laidout) moved))
;; L08 khu day dac gia lap
(setq dense (strcat *T-DIR* "run/day_dac.csv") f (open dense "w" "utf8") i 0 DP nil)
(repeat 60
  (write-line (strcat "D" (itoa i) "," (rtos (+ 1181000.0 (* 1.2 (/ i 10))) 2 3) "," (rtos (+ 576000.0 (* 1.2 (rem i 10))) 2 3)
                      ",1.5" (if (= (rem i 3) 0) ",coc tieu" (if (= (rem i 3) 1) ",bien bao 2 mat" ","))) f)
  (setq i (1+ i)))
(close f)
(setq r (bht:import-csv dense "DAYDAC"))
(foreach it (bht:pt-all) (if (bht:starts (car it) "DAYDAC-") (setq DP (cons (car it) DP))))
(bht:lbl-sync)
(setq OD1 (bht:lbl-overlaps DP))
(t-lbl-to-legacy DP)
(setq OD0 (bht:lbl-overlaps DP))
(bht:lbl-reset DP)
(setq OD2 (bht:lbl-overlaps DP))
(tchk "L08" "khu dày đặc giả lập 60 điểm lưới 1,2 m: chồng lấn giảm so với vị trí 0.3.2 (KHÔNG khẳng định hết chồng lấn)"
      (and (= (rv r 'added) 60) (< (cdr (assoc 'overlapped OD2)) (cdr (assoc 'overlapped OD0))) (= (t-lbl-dups) 0))
      (strcat "TRƯỚC (0.3.2): " (bht:lbl-overlap-text OD0) " || SAU: " (bht:lbl-overlap-text OD2)
              " || lần tạo đầu: " (bht:lbl-overlap-text OD1)))
(tchk "L09" "ĐIỂM RTK KHÔNG BỊ DI CHUYỂN sau mọi thao tác nhãn (526 POINT so tọa độ)"
      (= (t-pts-diff PTS0) 0) (strcat (itoa (length PTS0)) " điểm, lệch " (itoa (t-pts-diff PTS0))))

;; ---------- O: ho so doi tuong ----------
(setq nobj0 (length (bht:obj-ids)))
(setq ra (bht:obj-create "OBJ-T1" '(("nhom" . "COC_TIEU") ("so_tru" . "1")) '("BOT19-R-000020" "BOT19-R-000021") nil))
(setq o1 (bht:obj-overlap '("BOT19-R-000021")) o2 (bht:obj-overlap '("bot19-r-000021" "BOT19-R-000020")) o3 (bht:obj-overlap '("BOT19-R-000022")))
(tchk "O01" "phát hiện điểm đã thuộc hồ sơ + bộ điểm trùng khớp hồ sơ có sẵn"
      (and (car ra) (equal o1 '(("OBJ-T1") nil)) (equal o2 '(("OBJ-T1") ("OBJ-T1"))) (equal o3 '(nil nil))) (list ra o1 o2 o3))
(setq rb (bht:obj-create "OBJ-T2" nil '("BOT19-R-000021" "BOT19-R-000022") nil))
(tchk "O02" "tạo hồ sơ với điểm đã thuộc hồ sơ khác (không xác nhận) bị từ chối" (and (null (car rb)) (not (bht:obj-read "OBJ-T2"))) rb)
;; O03 lenh BHTDOITUONG voi dau vao gia lap (thay ham hoi, KHONG thay logic)
(setq SV-SEL bht:select-points SV-ASK bht:ask-string SV-GRP bht:ask-group SV-CNT bht:ask-count SV-SIDE bht:ask-side SV-ENT bht:pick-object)
(setq *ANS* nil *SEL* nil *ASKED* nil)
(defun bht:select-points (m) *SEL*)
(defun bht:ask-string (m d / hit)
  (setq *ASKED* (cons m *ASKED*))
  (setq hit (vl-some '(lambda (pr) (if (vl-string-search (car pr) m) pr)) *ANS*))
  (if hit (progn (setq *ANS* (vl-remove hit *ANS*)) (cdr hit)) (if d d "")))
(defun bht:ask-group (s) (if s s "0"))
(defun bht:ask-count (m d) (if d d ""))
(defun bht:ask-side (d) (if d d ""))
(setq *SEL* '("BOT19-R-000020" "BOT19-R-000021") *ANS* nil)
(c:BHTDOITUONG)
(setq n1 (length (bht:obj-ids)))
(setq *SEL* '("BOT19-R-000020" "BOT19-R-000021") *ANS* '(("X=Xem" . "M") ("XÁC NHẬN" . "K")))
(c:BHTDOITUONG)
(setq n2 (length (bht:obj-ids)))
(tchk "O03" "BHTDOITUONG chọn lại điểm đã có hồ sơ: mặc định (Enter) = HỦY, không tạo hồ sơ mới; M nhưng không xác nhận -> không tạo"
      (and (= n1 (1+ nobj0)) (= n2 (1+ nobj0))) (list nobj0 n1 n2))
(setq *SEL* '("BOT19-R-000021" "BOT19-R-000023") *ANS* '(("X=Xem" . "T")))
(c:BHTDOITUONG)
(tchk "O04" "BHTDOITUONG > T: thêm điểm đã chọn vào hồ sơ có sẵn (không tạo mới)"
      (and (= (length (bht:obj-ids)) (1+ nobj0)) (member "BOT19-R-000023" (bht:get-all (bht:obj-read "OBJ-T1") "pt"))
           (= (length (bht:get-all (bht:obj-read "OBJ-T1") "pt")) 3))
      (bht:get-all (bht:obj-read "OBJ-T1") "pt"))
(setq *SEL* '("BOT19-R-000030") *ANS* '(("ID đối tượng" . "OBJ-T3") ("Chèn ký hiệu" . "K")))
(c:BHTDOITUONG)
(setq *SEL* '("BOT19-R-000040" "BOT19-R-000041") *ANS* '(("ID đối tượng" . "OBJ-T4") ("Chèn ký hiệu" . "K")))
(c:BHTDOITUONG)
(setq *SEL* '("BOT19-R-000020") *ANS* '(("X=Xem" . "M") ("XÁC NHẬN" . "C") ("ID đối tượng" . "OBJ-T5") ("Chèn ký hiệu" . "K")))
(c:BHTDOITUONG)
(tchk "O05" "điểm chưa có hồ sơ -> tạo mới bình thường; M + xác nhận C -> hồ sơ mới dùng chung điểm (chủ động)"
      (and (bht:obj-read "OBJ-T3") (bht:obj-read "OBJ-T4") (bht:obj-read "OBJ-T5") (= (length (bht:obj-ids)) (+ nobj0 4))
           (equal (car (bht:obj-overlap '("BOT19-R-000020"))) '("OBJ-T1" "OBJ-T5")))
      (list (bht:obj-ids) (bht:obj-overlap '("BOT19-R-000020"))))
(setq bht:select-points SV-SEL bht:ask-string SV-ASK bht:ask-group SV-GRP bht:ask-count SV-CNT bht:ask-side SV-SIDE)
;; L10 che do uu tien ho so
(bht:meta-set "nhan_uu_tien_dt" "1")
(setq r (bht:lbl-sync))
(setq pr1 (list (t-lbl-str "BOT19-R-000020" "TEN") (t-lbl-str "BOT19-R-000020" "MOTA") (t-lbl-str "BOT19-R-000020" "CAODO"))
      pr2 (list (t-lbl-str "BOT19-R-000300" "TEN") (t-lbl-str "BOT19-R-000300" "CAODO")))
(bht:meta-set "nhan_uu_tien_dt" "0")
(setq r2 (bht:lbl-sync))
(tchk "L10" "chế độ ưu tiên hồ sơ: điểm thuộc hồ sơ chỉ còn nhãn TÊN; điểm khác đủ nhãn; tắt -> nhãn phụ trở lại"
      (and (car pr1) (null (cadr pr1)) (null (caddr pr1)) (car pr2) (cadr pr2) (t-lbl-str "BOT19-R-000020" "CAODO") (= (t-lbl-dups) 0))
      (list pr1 pr2 (rv r 'deleted) (rv r2 'created)))

;; ---------- K: ky hieu theo object_id ----------
(setq r (bht:symbol-sync nil))
(tchk "K01" "BHTKYHIEU lần đầu: tạo ký hiệu cho 4 hồ sơ (+ nhãn), không đụng INSERT cùng block không có XData BHT"
      (and (= (rv r 'created) 4) (= (rv r 'total) 4) (= (length (bht:tagged-pairs "TEXT" "BHT_KH" 1)) 4)) r)
(setq k1 (car (t-kh-ins-of "OBJ-T1")) d1 (entget k1))
(setq d1 (subst (list 10 575400.0 1187000.0 0.0) (assoc 10 d1) d1) d1 (subst (cons 50 0.5) (assoc 50 d1) d1)
      d1 (subst (cons 41 2.0) (assoc 41 d1) d1) d1 (subst (cons 42 2.0) (assoc 42 d1) d1))
(entmod d1) (entupd k1)
(setq kt (cdr (assoc "OBJ-T1" (bht:tagged-pairs "TEXT" "BHT_KH" 1))))
(t-move kt 5.0 0.0) (setq ktp (cdr (assoc 10 (entget kt))))
(setq rec (bht:obj-read "OBJ-T1")) (bht:obj-write "OBJ-T1" (bht:set rec "ma_hieu" "CT-01"))
(setq r (bht:symbol-refresh '("OBJ-T1")) d1b (entget (car (t-kh-ins-of "OBJ-T1"))) ktb (entget kt))
(tchk "K02" "sửa hồ sơ -> cập nhật ký hiệu: giữ vị trí/góc/tỷ lệ người dùng đặt, nhãn đổi chữ nhưng giữ chỗ"
      (and (equal (cdr (assoc 10 d1b)) '(575400.0 1187000.0 0.0) 1e-9) (equal (cdr (assoc 50 d1b)) 0.5 1e-9) (equal (cdr (assoc 41 d1b)) 2.0 1e-9)
           (= (cadr (bht:xget (car (t-kh-ins-of "OBJ-T1")) "BHT_KH")) "TAY") (= (cdr (assoc 1 ktb)) "Cọc tiêu CT-01")
           (equal (cdr (assoc 10 ktb)) ktp 1e-9) (= (length (t-kh-ins-of "OBJ-T1")) 1))
      (list (cdr (assoc 10 d1b)) (cdr (assoc 1 ktb)) r))
(setq rec (bht:set (bht:obj-read "OBJ-T1") "ma_hieu" "COC_TIEU_KM48+500"))
(tchk "K02a" "nhãn ký hiệu chỉ hiện tên nghiệp vụ và Km, không lộ object_id"
      (= (bht:kh-label "OBJ-T1" rec) "Cọc tiêu Km 48+500") (bht:kh-label "OBJ-T1" rec))
(bht:symbol-blocks)
(defun t-block-data (name / e d out done)
  (setq e (tblobjname "BLOCK" name) out nil done nil)
  (while (and e (not done) (setq e (entnext e)))
    (setq d (entget e))
    (if (= (cdr (assoc 0 d)) "ENDBLK") (setq done T) (setq out (cons d out))))
  (reverse out))
(setq bc (t-block-data "BHT_KH_COC_TIEU_V043") bk (t-block-data "BHT_KH_COT_KM_V043"))
(tchk "K02b" "block mặc định của Cọc tiêu và Cột Km đã được tạo"
      (and (>= (length bc) 10) (>= (length bk) 14)
           (vl-some '(lambda (d) (and (= (cdr (assoc 0 d)) "SOLID") (= (cdr (assoc 62 d)) 1))) bc)
           (vl-some '(lambda (d) (= (cdr (assoc 62 d)) 3)) bc)
           (vl-some '(lambda (d) (and (= (cdr (assoc 0 d)) "TEXT") (= (cdr (assoc 1 d)) "KM"))) bk))
      (list (length bc) (length bk)))
(setq k4 (car (t-kh-ins-of "OBJ-T4")) p4 (cdr (assoc 10 (entget k4))))
(bht:obj-add-points "OBJ-T4" '("BOT19-R-000042"))
(setq r (bht:symbol-refresh '("OBJ-T4")) p4b (cdr (assoc 10 (entget k4)))
      rec4 (bht:obj-read "OBJ-T4")
      pos4 (bht:obj-position rec4 (bht:pt-all))
      exp4 (car (bht:kh-auto-transform rec4 pos4 (bht:kh-scale-for rec4))))
(tchk "K03" "thêm điểm vào hồ sơ (ký hiệu tự động) -> ký hiệu dời tới vị trí tự động mới, cùng 1 thực thể (không xóa-vẽ lại)"
      (and (equal p4b exp4 1e-9) (not (equal p4 p4b 1e-9)) (entget k4) (= (rv r 'updated) 1)) (list p4 p4b))
(setq k3 (car (t-kh-ins-of "OBJ-T3")) kh-before (length (t-kh-ins)))
(bht:obj-delete "OBJ-T3")
(setq r (bht:symbol-sync nil))
(tchk "K04" "xóa hồ sơ -> chỉ ký hiệu + nhãn của hồ sơ đó bị gỡ; ký hiệu khác giữ nguyên thực thể"
      (and (null (t-kh-ins-of "OBJ-T3")) (null (assoc "OBJ-T3" (bht:tagged-pairs "TEXT" "BHT_KH" 1))) (entget k4) (entget k1)
           (= (length (t-kh-ins)) (1- kh-before)) (= (rv r 'created) 0))
      r)
(setq r (bht:symbol-sync nil))
(tchk "K05" "chạy lại BHTKYHIEU: không tạo / sửa / xóa gì (cập nhật theo ID, không xóa-vẽ lại)"
      (and (= (rv r 'created) 0) (= (rv r 'updated) 0) (= (rv r 'removed) 0) (= (rv r 'duplicates) 0) (= (rv r 'manual) 2)) r)
(setq r (bht:symbol-reset '("OBJ-T1")) d1c (entget (car (t-kh-ins-of "OBJ-T1"))))
(tchk "K06" "trả ký hiệu OBJ-T1 về tự động: vị trí = trung bình điểm RTK, góc 0, tỷ lệ cài đặt"
      (and (equal (cdr (assoc 10 d1c)) (bht:obj-position (bht:obj-read "OBJ-T1") (bht:pt-all)) 1e-9) (equal (cdr (assoc 50 d1c)) 0.0 1e-9)
           (equal (cdr (assoc 41 d1c)) (bht:kh-scale) 1e-9))
      (list (cdr (assoc 10 d1c)) (car r)))

;; ---------- P: anh ----------
(setq r (tsafe "P01" "nhập ảnh" '(lambda () (bht:photo-import-tsv *PH* T))))
(if r (tchk "P01" "nhập 205 ảnh: 203 ký hiệu (2 ảnh GPS 0,0 không có ký hiệu)" (and (= (rv r 'added) 205) (= (t-mk-count) 203)) (rv r 'sync)))
(setq r (bht:photo-import-tsv *PH* T))
(tchk "P02" "nhập lại chỉ mục ảnh: không trùng ký hiệu" (and (= (rv r 'added) 0) (= (t-mk-count) 203) (= (rv (rv r 'sync) 'created) 0)
                                                          (= (rv (rv r 'sync) 'duplicates) 0)) (rv r 'sync))
(setq before nil)
(foreach p (bht:tagged-pairs "INSERT" "BHT_ANHPT" 1) (setq before (cons (cons (car p) (cdr (assoc 10 (entget (cdr p))))) before)))
(bht:meta-set "crs_idx" "2") (setq r1 (bht:photo-sync))
(bht:meta-set "crs_idx" "1") (setq r2 (bht:photo-sync) back 0)
(foreach p (bht:tagged-pairs "INSERT" "BHT_ANHPT" 1)
  (if (equal (cdr (assoc 10 (entget (cdr p)))) (cdr (assoc (car p) before)) 1e-9) (setq back (1+ back))))
(tchk "P03" "đồng bộ lại hệ tọa độ ảnh (đổi KTT rồi đổi lại): 203 ký hiệu dời rồi về đúng chỗ, không trùng; RTK không đổi"
      (and (= (rv r1 'updated) 203) (= back 203) (= (t-mk-count) 203) (= (t-pts-diff PTS0) 0))
      (list (rv r1 'updated) back))
(setq rl (bht:photo-relink *MOVED*) stt (bht:photo-stats) o1 (bht:photo-open "BOT19-P-000001"))
(tchk "P04" "thư mục ảnh chuyển chỗ: BHTTHUMUCANH chỉ tới thư mục mới -> 205/205 JPG tìm thấy, mở đúng file"
      (and (equal rl '(205 0)) (= (rv stt 'jpg-found) 205) (car o1) (wcmatch (strcase (cadr o1)) "*ANH_DA_DOI*"))
      (list rl (cadr o1)))
(setq mk (car (t-mk "BOT19-P-000010")) pf (bht:photos-for-ent mk) il (bht:info-lines mk))
(tchk "P05" "chọn ký hiệu ảnh -> đúng mã ảnh để xem (mức hàm; không mở trình xem)"
      (and (vl-some '(lambda (l) (vl-string-search "BOT19-P-000010" l)) il) (car (bht:photo-open "BOT19-P-000010"))) (car il))
(setq nr0 (length (bht:tagged-pairs "IMAGE" "BHT_ANHRS" 1)))
(tchk "P06" "nhập / đồng bộ ảnh KHÔNG tự chèn raster hàng loạt" (= nr0 0) nr0)
(setq r1 (bht:raster-insert "BOT19-P-000010" nil 8.0) ld (bht:leader-make "BOT19-P-000010"))
(setq ldd (if ld (entget ld)) img (if (eq (car r1) T) (entget (cadr r1))))
(tchk "P07" "chèn raster 1 ảnh + đường dẫn (LINE) từ ký hiệu ảnh tới raster"
      (and (eq (car r1) T) ld (equal (cdr (assoc 10 ldd)) (cdr (assoc 10 (entget mk))) 1e-9) (equal (cdr (assoc 11 ldd)) (cdr (assoc 10 img)) 1e-9)
           (= (cdr (assoc 8 ldd)) "BHT_ANH_DAN"))
      (list r1 ld))
(setq e (cadr r1)) (t-move e 10.0 0.0)
(setq lr (bht:leader-sync) ldd (entget ld))
(tchk "P08" "dời raster -> đường dẫn cập nhật theo" (and (equal lr '(1 0)) (equal (cdr (assoc 11 ldd)) (cdr (assoc 10 (entget e))) 1e-9)) lr)
(setq r1b (bht:raster-insert "BOT19-P-000020" nil 8.0))
(tchk "M01" "bản vẽ đang ở tab Layout (TILEMODE=0): điểm/nhãn/ký hiệu/ảnh/raster BHT đều tạo trong MODEL; TILEMODE trả lại như cũ"
      (and (= (getvar "TILEMODE") 0) (null (bht:ents-outside-model)) (eq (car r1b) T)
           (= (cdr (assoc 410 (entget (cadr r1b)))) "Model") (= (cdr (assoc 410 (entget (t-pt-ent "BOT19-R-000001")))) "Model"))
      (list (getvar "TILEMODE") (getvar "CTAB") (length (bht:ents-outside-model))))

;; ---------- W: thu tu hien thi ----------
(bht:layer "IRT_GOOGLE" 7)
(setq tm0 (getvar "TILEMODE")) (setvar "TILEMODE" 1)
(setq cl (getvar "CLAYER")) (setvar "CLAYER" "IRT_GOOGLE") (setvar "CMDECHO" 0)
(setq le (entlast)) (vl-cmdf "_.-IMAGE" "_Attach" (strcat *T-DIR* "irt/google_sat_18_x.jpg") '(575000.0 1187000.0 0.0) 50.0 0.0)
(while (= 1 (logand 1 (getvar "CMDACTIVE"))) (command ""))
(setq IRT (if (not (equal le (entlast))) (entlast)))
(setvar "CLAYER" "0")
(setq le (entlast)) (vl-cmdf "_.-IMAGE" "_Attach" (strcat *T-DIR* "khac/anh_khac.jpg") '(575100.0 1187000.0 0.0) 20.0 0.0)
(while (= 1 (logand 1 (getvar "CMDACTIVE"))) (command ""))
(setq OTH (if (not (equal le (entlast))) (entlast)))
(setvar "CLAYER" cl) (setvar "TILEMODE" tm0)
(setq OTHD (if OTH (entget OTH)) IRTD (if IRT (entget IRT)))
(setq g (bht:draworder-groups))
(tchk "W01" "nhận diện: ảnh nền kiểu IRT (layer IRT_GOOGLE, file google_sat_*) là IRT; ảnh khác (layer 0, thư mục 'khac') KHÔNG bị coi là IRT; raster BHT riêng"
      (and IRT OTH (equal (cdr (assoc 'irt g)) (list IRT)) (member OTH (cdr (assoc 'other-images g))) (= (length (cdr (assoc 'raster g))) 2))
      (list (length (cdr (assoc 'irt g))) (length (cdr (assoc 'other-images g))) (length (cdr (assoc 'raster g)))))
(setq r (tsafe "W02" "BHTTHUTUVE" '(lambda () (bht:draworder-sync))))
(setq se (t-sortents) g (bht:draworder-groups)
      rl (t-rank-range (cdr (assoc 'labels g)) se) rm (t-rank-range (cdr (assoc 'mid g)) se)
      rr (t-rank-range (cdr (assoc 'raster g)) se) ri (t-rank-range (cdr (assoc 'irt g)) se))
(setq ss (ssget "_X" '((410 . "Model"))) i 0 lowest T)
(while (< i (sslength ss))
  (setq e (ssname ss i))
  (if (and (not (eq e IRT)) (<= (t-rank e se) (cadr ri))) (setq lowest nil))
  (setq i (1+ i)))
(if r (tchk "W02" "thứ tự hiển thị (bảng SORTENTS): nhãn > ký hiệu/POINT/ký hiệu ảnh/đường dẫn > raster BHT > ... > ảnh nền IRT dưới cùng"
            (and se (> (car rl) (cadr rm)) (> (car rm) (cadr rr)) lowest (> (t-rank OTH se) (cadr ri)))
            (strcat "SORTENTS " (itoa (length se)) " mục | nhãn " (vl-princ-to-string rl) " giữa " (vl-princ-to-string rm)
                    " raster " (vl-princ-to-string rr) " IRT " (vl-princ-to-string ri) " | " (vl-princ-to-string r))))
(tchk "W03" "ảnh IRT và ảnh khác: dữ liệu thực thể không bị sửa (chỉ thứ tự hiển thị)"
      (and (equal (entget IRT) IRTD) (equal (entget OTH) OTHD)) nil)

;; ---------- trang thai tay de phien B kiem tra sau khi luu ----------
(setq me (t-lbl-ent "BOT19-R-000150" "TEN")) (t-move me 2.0 -3.0) (bht:lbl-sync)
(setq MANPOS (t-lbl-pos "BOT19-R-000150" "TEN"))
(setq k4 (car (t-kh-ins-of "OBJ-T4")) d4 (entget k4))
(setq d4 (subst (list 10 574530.0 1193960.0 0.0) (assoc 10 d4) d4) d4 (subst (cons 50 1.0) (assoc 50 d4) d4))
(entmod d4) (entupd k4) (bht:symbol-sync nil)
(setq T4POS (cdr (assoc 10 (entget k4))))
;; ---------- N + K ----------
(setq dd (t-snap-diff SNAP))
(tchk "N01" "thực thể ngoài BHT (kể cả TEXT cùng layer, INSERT cùng block BHT_KH_*, XData app khác) không bị xóa/sửa"
      (and (= (cadr dd) 0) (= (caddr dd) 0) (entget F1) (entget F2) (entget F3)) dd)
(setq k (bht:check))
(tchk "K07" "BHTKT: 0 lỗi" (= (car k) 0) (strcat (itoa (car k)) " lỗi, " (itoa (cadr k)) " cảnh báo"))
(foreach l (caddr k) (if (or (bht:starts l "LỖI") (bht:starts l "CẢNH BÁO")) (tlog (strcat "   KT: " l))))
(foreach l (bht:status-lines) (tlog (strcat "   TRẠNG THÁI: " l)))
(t-write-state "A" (list (cons "points" (length (bht:pt-all))) (cons "labels" (length (bht:tagged-pairs "TEXT" "BHT_NHAN" 2)))
                         (cons "states" (t-lbl-states)) (cons "markers" (t-mk-count)) (cons "photos" (length (bht:rec-keys "PHOTO")))
                         (cons "objs" (bht:obj-ids)) (cons "kh" (length (t-kh-ins))) (cons "rasters" (length (bht:tagged-pairs "IMAGE" "BHT_ANHRS" 1)))
                         (cons "leaders" (length (bht:leader-pairs))) (cons "t1pos" (cdr (assoc 10 (entget (car (t-kh-ins-of "OBJ-T1"))))))
                         (cons "sortents" (length se)) (cons "manpos" MANPOS) (cons "t4pos" T4POS)
                         (cons "lblpos" (t-lbl-positions))))
(tend "A")
(princ)
