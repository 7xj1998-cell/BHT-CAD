;;; BHT 0.3.3 - phien L: mo BAN SAO ban ve da lam bang BHT 0.3.2 (test_A_saveas.dwg cua 0.3.2:
;;; 531 diem, nhan TEN/MOTA/CAODO/ID, 203 ky hieu anh, 205 anh, 1 raster, ho so OBJ-000001, ky hieu)
(load (strcat (getenv "BHT_TEST_DIR") "/t_common.lsp"))
(tbegin "L")
(defun t-dump-recs (/ out)
  (setq out nil)
  (foreach dn '("OBJ" "PHOTO" "DATASET" "ROUTE" "SEG" "MOC")
    (foreach r (vl-catch-all-apply 'bht:rec-all (list dn)) (if (listp r) (setq out (cons (cons (strcat dn "|" (car r)) (cdr r)) out)))))
  out)
;; truoc khi nap 0.3.3: chi doc
(setq e (tload))
(tchk "L00" "nạp BHT-5.0 trên bản vẽ 0.3.2" (and (null e) (= *bht-version* "0.6.55")) e)
(setq *bht-no-launch* T)
(setq REC0 (t-dump-recs) PTS0 (t-pt-coords) POS0 (t-lbl-positions)
      C0 (list (length (bht:pt-all)) (t-lbl-count "TEN") (t-lbl-count "MOTA") (t-lbl-count "CAODO") (t-lbl-count "ID")
               (t-mk-count) (length (bht:rec-keys "PHOTO")) (length (bht:tagged-pairs "IMAGE" "BHT_ANHRS" 1)) (bht:obj-ids) (length (t-kh-ins))))
(tlog (strcat "   bản vẽ 0.3.2: điểm/TEN/MOTA/CAODO/ID/ký hiệu ảnh/ảnh/raster/hồ sơ/ký hiệu = " (vl-princ-to-string C0)
              " | bản ghi XRecord " (itoa (length REC0))))
(setq KH0 (mapcar '(lambda (p) (cons (car p) (cdr (assoc 10 (entget (cdr p)))))) (t-kh-ins)))
(setq OVB (bht:lbl-overlaps nil))
;; L01
(setq r (tsafe "L01" "BHTNHANDIEM" '(lambda () (bht:lbl-sync))))
(setq st (t-lbl-states) POS1 (t-lbl-positions) moved 0)
(foreach pp POS0 (if (not (equal (cdr pp) (cdr (assoc (car pp) POS1)) 1e-9)) (setq moved (1+ moved))))
(if r (tchk "L01" "cập nhật nhãn lần đầu bằng 0.3.3: không tạo/xóa, KHÔNG dời nhãn nào (nâng cấp XData: nhãn ở vị trí mặc định -> tự động, khác -> tay)"
            (and (= (rv r 'created) 0) (= (rv r 'deleted) 0) (= moved 0) (= (caddr st) 0) (= (t-lbl-dups) 0))
            (strcat (vl-princ-to-string r) " | (tự động tay cũ)=" (vl-princ-to-string st) " | nhãn bị dời " (itoa moved))))
(tchk "L02" "điểm RTK, bản ghi hồ sơ/ảnh/dataset giữ nguyên sau khi mở + cập nhật nhãn"
      (and (= (t-pts-diff PTS0) 0) (equal (vl-remove-if '(lambda (x) (bht:starts (car x) "PHOTO|")) (t-dump-recs))
                                          (vl-remove-if '(lambda (x) (bht:starts (car x) "PHOTO|")) REC0))
           (= (length (t-dump-recs)) (length REC0)))
      (list (t-pts-diff PTS0) (length (t-dump-recs))))
;; L03 ky hieu
(setq r (bht:symbol-sync nil) moved 0)
(foreach p KH0 (if (not (equal (cdr p) (cdr (assoc 10 (entget (car (t-kh-ins-of (car p)))))) 1e-9)) (setq moved (1+ moved))))
(tchk "L03" "ký hiệu 0.3.2: nhận ra theo object_id, không vẽ trùng, không dời" (and (= (rv r 'created) 0) (= (rv r 'duplicates) 0) (= moved 0) (= (length (t-kh-ins)) (last C0))) r)
;; L04 anh
(setq r (bht:photo-sync) stt (bht:photo-stats))
(tchk "L04" "ảnh 0.3.2: đồng bộ không tạo trùng ký hiệu; 205 bản ghi" (and (= (rv r 'created) 0) (= (rv r 'duplicates) 0) (= (t-mk-count) 203) (= (length (bht:rec-keys "PHOTO")) 205)) (list r stt))
;; L05 BHTKT phat hien thuc the trong Layout
(setq OUT0 (bht:ents-outside-model) k (bht:check))
(tchk "L05" "BHTKT: phát hiện thực thể BHT nằm trong Layout (bản vẽ 0.3.2 làm khi đang ở tab Layout) và gợi ý BHTVEMODEL"
      (and (> (length OUT0) 0) (vl-some '(lambda (l) (vl-string-search "BHTVEMODEL" l)) (caddr k)))
      (strcat (itoa (length OUT0)) " thực thể | " (itoa (car k)) " lỗi, " (itoa (cadr k)) " cảnh báo"))
(foreach l (caddr k) (if (or (bht:starts l "LỖI") (bht:starts l "CẢNH BÁO")) (tlog (strcat "   KT: " l))))
;; L06 chuyen ve Model
(setq LBLTXT0 (mapcar '(lambda (p) (cons (car p) (cdr (assoc 1 (entget (cdr p)))))) (bht:tagged-pairs "TEXT" "BHT_NHAN" 2)))
(setq r (bht:move-all-to-model))
(setq LBLTXT1 (mapcar '(lambda (p) (cons (car p) (cdr (assoc 1 (entget (cdr p)))))) (bht:tagged-pairs "TEXT" "BHT_NHAN" 2)))
(setq POS2 (t-lbl-positions) moved 0)
(foreach pp POS1 (if (not (equal (cdr pp) (cdr (assoc (car pp) POS2)) 1e-9)) (setq moved (1+ moved))))
(setq rest (bht:ents-outside-model))
(tchk "L06" "BHTVEMODEL: chuyển về Model, tọa độ điểm/nhãn và XData giữ nguyên, số lượng không đổi; chỉ raster bị bỏ qua (báo chèn lại)"
      (and (= (t-pts-diff PTS0) 0) (= moved 0) (= (length LBLTXT1) (length LBLTXT0))
           (equal (vl-sort LBLTXT0 '(lambda (a b) (< (car a) (car b)))) (vl-sort LBLTXT1 '(lambda (a b) (< (car a) (car b)))))
           (= (length rest) (cadr r)) (vl-every '(lambda (e) (= (cdr (assoc 0 (entget e))) "IMAGE")) rest)
           (= (length (bht:pt-all)) (car C0)) (= (t-mk-count) 203) (= (length (t-kh-ins)) (last C0)))
      (list r (length rest) moved))
(setq r (bht:lbl-sync) st2 (t-lbl-states))
(tchk "L07" "sau khi chuyển: trạng thái nhãn giữ nguyên, cập nhật nhãn không tạo/xóa" (and (equal st2 st) (= (rv r 'created) 0) (= (rv r 'deleted) 0)) (list st st2))
;; L08 sap nhan lai toan bo (BHTSAPNHAN > tat ca)
(setq OVB2 (bht:lbl-overlaps nil) r (bht:lbl-sync-scope 'ALL) OVA (bht:lbl-overlaps nil) st3 (t-lbl-states))
(tchk "L08" "BHTSAPNHAN tất cả trên bản vẽ 0.3.2: chồng lấn giảm; nhãn tay (nếu có) giữ nguyên; điểm RTK không dời"
      (and (< (cdr (assoc 'overlapped OVA)) (cdr (assoc 'overlapped OVB2))) (= (cadr st3) (cadr st)) (= (t-pts-diff PTS0) 0) (= (t-lbl-dups) 0))
      (strcat "TRƯỚC: " (bht:lbl-overlap-text OVB2) " || SAU: " (bht:lbl-overlap-text OVA) " | nhãn tay " (itoa (cadr st3))))
(setq r (bht:draworder-sync) se (t-sortents) g (bht:draworder-groups)
      rl (t-rank-range (cdr (assoc 'labels g)) se) rm (t-rank-range (cdr (assoc 'mid g)) se))
(tchk "L09" "BHTTHUTUVE trên bản vẽ 0.3.2 (sau khi chuyển về Model): nhãn nằm trên ký hiệu/điểm" (and (> (car rl) (cadr rm))) (list r rl rm))
(setq k (bht:check))
(tchk "L10" "BHTKT sau nâng cấp: 0 lỗi" (= (car k) 0) (strcat (itoa (car k)) " lỗi, " (itoa (cadr k)) " cảnh báo"))
(foreach l (caddr k) (if (or (bht:starts l "LỖI") (bht:starts l "CẢNH BÁO")) (tlog (strcat "   KT: " l))))
(t-write-state "L" (list (cons "points" (length (bht:pt-all))) (cons "labels" (length (bht:tagged-pairs "TEXT" "BHT_NHAN" 2)))
                         (cons "states" (t-lbl-states)) (cons "markers" (t-mk-count)) (cons "photos" (length (bht:rec-keys "PHOTO")))
                         (cons "objs" (bht:obj-ids)) (cons "recs" (length (t-dump-recs))) (cons "lblpos" (t-lbl-positions))))
(tend "L")
(princ)
