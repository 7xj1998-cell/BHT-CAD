(defun origin-entities (oid)
  (mapcar 'cdr (vl-remove-if-not '(lambda (pair) (= (car pair) oid))
    (bht:tagged-pairs "INSERT" "BHT_SIGN_ORIGIN" 1))))
(defun origin-correct (oid / ok e p d)
  (setq ok T)
  (foreach e (origin-entities oid)
    (setq d (entget e) p (bht:pt-find (cadr (bht:xget e "BHT_SIGN_ORIGIN")) (bht:pt-all)))
    (if (not (and p (equal (cdr (assoc 10 d)) (bht:pv p 'xyz) 1e-8)
         (= (cdr (assoc 8 d)) "BHT_KYHIEU") (= (cdr (assoc 62 d)) 7))) (setq ok nil)))
  ok)
(bht:layer "ORIGIN_TEST_POINTS" 3)
(setq origin-p1 (entmakex '((0 . "POINT") (8 . "ORIGIN_TEST_POINTS") (10 250.0 40.0 2.0)))
      origin-p2 (entmakex '((0 . "POINT") (8 . "ORIGIN_TEST_POINTS") (10 254.0 42.0 2.0))))
(bht:pt-write-xdata origin-p1 "ORIGIN-1" "ORIGIN" "1" "Chân 1" 40.0 250.0 2.0 "BIEN_BAO" "test" "" "")
(bht:pt-write-xdata origin-p2 "ORIGIN-2" "ORIGIN" "2" "Chân 2" 42.0 254.0 2.0 "BIEN_BAO" "test" "" "")
(setq origin-rtk-before (list (entget origin-p1 '("BHT_PT")) (entget origin-p2 '("BHT_PT"))))
(bht:obj-create "OBJ-ORIGIN" '(("nhom" . "BIEN_BAO") ("so_tru" . "2") ("ma_hieu" . "W.207a")) '("ORIGIN-1" "ORIGIN-2") T)
(bht:kh-free-apply "OBJ-ORIGIN" '(260.0 50.0 2.0) 0.7 nil)
(signs-check "origin-two-X-centers-independent-from-offset-sign" (and (= (length (origin-entities "OBJ-ORIGIN")) 2) (origin-correct "OBJ-ORIGIN")))
(setq origin-disk (entget (entnext (tblobjname "BLOCK" "BHT_SIGN_ORIGIN_V0634")) ))
(signs-check "origin-exact-filled-circular-block" (and (= (cdr (assoc 0 origin-disk)) "LWPOLYLINE") (= (cdr (assoc 90 origin-disk)) 2)
  (= (cdr (assoc 70 origin-disk)) 1) (equal (cdr (assoc 43 origin-disk)) 0.07 1e-8)
  (= (length (vl-remove-if-not '(lambda (pair) (and (= (car pair) 42) (= (cdr pair) 1.0))) origin-disk)) 2)))
(setq origin-before (mapcar '(lambda (e) (entget e '("BHT_SIGN_ORIGIN"))) (origin-entities "OBJ-ORIGIN")))
(bht:symbol-sync '("OBJ-ORIGIN"))
(signs-check "origin-refresh-idempotent" (equal origin-before (mapcar '(lambda (e) (entget e '("BHT_SIGN_ORIGIN"))) (origin-entities "OBJ-ORIGIN"))))
(bht:kh-free-apply "OBJ-ORIGIN" '(270.0 55.0 2.0) 2.8 '((257.0 45.0 2.0)))
(signs-check "origin-stays-at-X-after-sign-move-rotation-waypoints" (origin-correct "OBJ-ORIGIN"))
(bht:api-sign-scale "2" "0.75")
(signs-check "origin-size-follows-sign-scale" (vl-every '(lambda (e) (equal (cdr (assoc 41 (entget e))) 2.0 1e-8)) (origin-entities "OBJ-ORIGIN")))
(bht:api-sign-fill "0")
(signs-check "origin-keeps-fill-when-sign-background-off" (and (origin-correct "OBJ-ORIGIN") (equal origin-disk (entget (entnext (tblobjname "BLOCK" "BHT_SIGN_ORIGIN_V0634"))))))
(setq origin-layer (tblobjname "LAYER" "ORIGIN_TEST_POINTS"))
(entmod (bht:dxf-put (entget origin-layer) 62 -3))
(bht:symbol-sync '("OBJ-ORIGIN"))
(signs-check "origin-visible-on-symbol-layer-with-survey-layer-off" (and (origin-correct "OBJ-ORIGIN") (> (cdr (assoc 62 (tblsearch "LAYER" "BHT_KYHIEU"))) 0)))
(entmod (bht:dxf-put (entget origin-layer) 62 3))
(setq origin-rec (bht:obj-read "OBJ-ORIGIN"))
(bht:obj-write "OBJ-ORIGIN" (bht:set (bht:set-all origin-rec "pt" '("ORIGIN-1" "ORIGIN-1")) "so_tru" "1"))
(bht:kh-free-apply "OBJ-ORIGIN" '(250.0 40.0 2.0) 0.0 nil)
(signs-check "origin-at-G-with-no-leader-and-deduplicated-source" (and (= (length (origin-entities "OBJ-ORIGIN")) 1) (origin-correct "OBJ-ORIGIN") (null (support-lines "OBJ-ORIGIN"))))
(setq origin-duplicate (bht:insert "BHT_SIGN_ORIGIN_V0634" '(250.0 40.0 2.0) "BHT_KYHIEU" 1.0))
(entmod (append (entget origin-duplicate) (list (list -3 (list "BHT_SIGN_ORIGIN" '(1000 . "OBJ-ORIGIN") '(1000 . "ORIGIN-1"))))))
(bht:symbol-sync '("OBJ-ORIGIN"))
(signs-check "origin-removes-duplicate-insert" (= (length (origin-entities "OBJ-ORIGIN")) 1))
(bht:obj-write "OBJ-ORIGIN" (bht:set-all origin-rec "pt" '("MISSING")))
(bht:symbol-sync '("OBJ-ORIGIN"))
(signs-check "origin-removes-missing-survey-source" (null (origin-entities "OBJ-ORIGIN")))
(bht:obj-write "OBJ-ORIGIN" origin-rec)
(bht:symbol-sync '("OBJ-ORIGIN"))
(signs-check "origin-restores-two-source-markers" (= (length (origin-entities "OBJ-ORIGIN")) 2))
(bht:obj-write "OBJ-ORIGIN" (bht:set origin-rec "nhom" "KHAC"))
(bht:symbol-sync '("OBJ-ORIGIN"))
(signs-check "origin-keeps-markers-for-two-post-other-board" (= 2 (length (origin-entities "OBJ-ORIGIN"))))
(bht:obj-write "OBJ-ORIGIN" origin-rec)
(bht:symbol-sync '("OBJ-ORIGIN"))
(signs-check "origin-keeps-original-survey-and-XData" (equal origin-rtk-before (list (entget origin-p1 '("BHT_PT")) (entget origin-p2 '("BHT_PT")))))
(bht:symbol-delete "OBJ-ORIGIN")
(signs-check "origin-symbol-delete-cleans-markers" (null (origin-entities "OBJ-ORIGIN")))
(bht:symbol-sync '("OBJ-ORIGIN"))
(bht:obj-delete "OBJ-ORIGIN")
(signs-check "origin-object-delete-cleans-markers-immediately" (and (null (origin-entities "OBJ-ORIGIN")) (entget origin-p1) (entget origin-p2)))
(bht:obj-create "OBJ-ORIGIN" origin-rec '("ORIGIN-1" "ORIGIN-2") T)
(bht:symbol-sync '("OBJ-ORIGIN"))
(bht:rec-delete "OBJ" "OBJ-ORIGIN")
(bht:symbol-sync nil)
(signs-check "origin-orphan-cleanup" (null (origin-entities "OBJ-ORIGIN")))
(bht:api-sign-fill "1") (bht:api-sign-scale "1" "1")
(princ "\nORIGIN-TEST-COMPLETED")
