(setq *sign0610-reopen-fail* 0)
(defun sign0610-reopen-check (name ok) (princ (strcat "\n" (if ok "PASS " "FAIL ") name)) (if (not ok) (setq *sign0610-reopen-fail* (1+ *sign0610-reopen-fail*))))
(setq qr-h (bht:obj-read "OBJ-QA0610-H") qr-km (bht:obj-read "OBJ-QA0610-KM") qr-bridge (bht:obj-read "OBJ-QA0610-BRIDGE"))
(sign0610-reopen-check "reopen-hectometre" (= (bht:kh-label "OBJ-QA0610-H" qr-h) "H9/39"))
(sign0610-reopen-check "reopen-km-in-block" (= (bht:kh-block qr-km) "BHT_KH_COT_KM_V0611_39"))
(sign0610-reopen-check "reopen-bridge-data" (and (= (bht:get qr-bridge "bridge_name") "CẦU YÊN CHÂU") (= (bht:get qr-bridge "sign_chainage") "Km252+831") (= (bht:get qr-bridge "road_name") "QL.6")))
(sign0610-reopen-check "reopen-bridge-geometry" (wcmatch (bht:kh-block qr-bridge) "BHT_I439_V0611_*"))
(setq qr-label (cdr (assoc "OBJ-QA0610-H" (bht:tagged-pairs "TEXT" "BHT_KH" 1))) qr-before (entget qr-label))
(bht:symbol-sync '("OBJ-QA0610-H"))
(sign0610-reopen-check "reopen-repeat-idempotent" (equal qr-before (entget qr-label)))
(princ (strcat "\nSIGN0610-REOPEN-FAIL=" (itoa *sign0610-reopen-fail*)))
(princ)
