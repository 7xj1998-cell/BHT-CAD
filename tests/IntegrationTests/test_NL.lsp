;;; BHT 0.6.55 - phien NL: BAN SAO ban ve lam bang BHT 0.3.2 (legacy_032_src.dwg) mo bang 5.0 + BHT.Bridge.
(load (strcat (getenv "BHT_TEST_DIR") "/t_common.lsp"))
(tbegin "NL")
(setq e (tload))
(tchk "K00" "nạp BHT-5.0 trên bản vẽ 0.3.2" (and (null e) (= *bht-version* "0.6.55")) e)
(setq NP (length (bht:pt-all)) NPH (length (bht:rec-keys "PHOTO")) NO (length (bht:obj-ids)) PC0 (t-pt-coords))
(tlog (strcat "   bản vẽ 0.3.2: điểm " (itoa NP) ", ảnh " (itoa NPH) ", hồ sơ " (itoa NO)))
(setq e (t-netload "BHT.Bridge.dll"))
(t-dump (t-run "NL_L1.txt"))
(command "BHTNETDUMP" (t-run "NL_C1.txt"))
(setq cmp (t-cmp (t-run "NL_L1.txt") (t-run "NL_C1.txt")))
(tchk "K01" "C# đọc bản vẽ 0.3.2 giống hệt Lisp 5.0 (điểm, hồ sơ, ảnh, meta, JPG)" (and (null e) (car cmp)) cmp)
(tchk "K02" "C# đọc đủ điểm / 205 ảnh / hồ sơ của bản vẽ 0.3.2"
      (and (= (t-count-prefix (t-run "NL_C1.txt") "P|") NP) (> NP 0) (= (t-count-prefix (t-run "NL_C1.txt") "R|PHOTO|") 205) (= (t-count-prefix (t-run "NL_C1.txt") "R|OBJ|") NO))
      (list NP NPH NO))
(setq owners (bht:pt-owner-map) FREE nil)
(foreach it (bht:pt-all) (if (and (null FREE) (not (assoc (car it) owners))) (setq FREE (list (bht:pv (cdr it) 'id)))))
(setq NID (bht:obj-next-id))
(command "BHTNETTAO" "." (car FREE) "1" "." "2" "." "." "K")
(tchk "K03" "C# tạo hồ sơ trên bản vẽ 0.3.2: ID nối tiếp đúng (không dùng lại số đã xóa), Lisp đọc được" (and (bht:obj-read NID) (= (length (bht:obj-ids)) (1+ NO))) NID)
(setq own (car (vl-remove-if-not '(lambda (x) (/= (car x) (strcase (car FREE)))) (bht:pt-owner-map))))
(setq n0 (length (bht:obj-ids)))
(if own (command "BHTNETTAO" "." (car own) "1" "." "." "." "." "K"))
(tchk "K04" "C# không tạo trùng trên điểm đã có hồ sơ từ 0.3.2" (and own (= (length (bht:obj-ids)) n0)) own)
(tchk "K05" "không POINT nào bị dời" (equal (vl-sort PC0 '(lambda (a b) (< (car a) (car b)))) (vl-sort (t-pt-coords) '(lambda (a b) (< (car a) (car b))))) nil)
(tend "NL")
(princ)
