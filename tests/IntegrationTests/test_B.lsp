;;; BHT 0.3.3 - phien B: MO LAI ban SAVEAS 2018 cua phien A (A_out.dwg)
(load (strcat (getenv "BHT_TEST_DIR") "/t_common.lsp"))
(tbegin "B")
(setq e (tload))
(tchk "B00" "nạp BHT-5.0 trên bản vẽ đã lưu (SAVEAS 2018)" (and (null e) (= *bht-version* "0.6.55") (wcmatch (strcase (getvar "DWGNAME")) "A_OUT*")) (getvar "DWGNAME"))
(setq S (t-read-state "A"))
(defun sv (k) (cdr (assoc k S)))
(setq st (t-lbl-states))
(tchk "B01" "sau khi mở lại: số điểm, nhãn, trạng thái nhãn (tự động/tay), ký hiệu ảnh, ảnh, hồ sơ, ký hiệu, raster, đường dẫn giữ nguyên"
      (and S (= (length (bht:pt-all)) (sv "points")) (= (length (bht:tagged-pairs "TEXT" "BHT_NHAN" 2)) (sv "labels"))
           (equal st (sv "states")) (= (t-mk-count) (sv "markers")) (= (length (bht:rec-keys "PHOTO")) (sv "photos"))
           (equal (bht:obj-ids) (sv "objs")) (= (length (t-kh-ins)) (sv "kh"))
           (= (length (bht:tagged-pairs "IMAGE" "BHT_ANHRS" 1)) (sv "rasters")) (= (length (bht:leader-pairs)) (sv "leaders")))
      (list (length (bht:pt-all)) st (t-mk-count) (bht:obj-ids) (length (t-kh-ins))))
(setq POS (t-lbl-positions) diff 0)
(foreach pp (sv "lblpos") (if (not (equal (cdr pp) (cdr (assoc (car pp) POS)) 1e-9)) (setq diff (1+ diff))))
(tchk "B02" "vị trí mọi nhãn giữ nguyên sau lưu / mở lại" (= diff 0) (strcat (itoa (length POS)) " nhãn, lệch " (itoa diff)))
(setq r (bht:lbl-sync) q (t-lbl-pos "BOT19-R-000150" "TEN"))
(tchk "B03" "cập nhật nhãn sau mở lại: không tạo/xóa; nhãn dời tay vẫn giữ nguyên vị trí và trạng thái TAY"
      (and (= (rv r 'created) 0) (= (rv r 'deleted) 0) (bht:pt-near q (sv "manpos") 1e-6) (eq (bht:lbl-state (t-lbl-ent "BOT19-R-000150" "TEN")) 'TAY))
      (list r q))
(setq r (bht:symbol-sync nil) p4 (cdr (assoc 10 (entget (car (t-kh-ins-of "OBJ-T4"))))))
(tchk "B04" "cập nhật ký hiệu sau mở lại: không tạo trùng; ký hiệu đặt tay (OBJ-T4) giữ vị trí"
      (and (= (rv r 'created) 0) (= (rv r 'duplicates) 0) (equal p4 (sv "t4pos") 1e-9)) (list r p4))
(setq se (t-sortents) g (bht:draworder-groups)
      rl (t-rank-range (cdr (assoc 'labels g)) se) rm (t-rank-range (cdr (assoc 'mid g)) se) rr (t-rank-range (cdr (assoc 'raster g)) se)
      ri (t-rank-range (cdr (assoc 'irt g)) se))
(tchk "B05" "thứ tự hiển thị lưu trong bản vẽ (SORTENTS) còn đúng sau mở lại"
      (and (> (car rl) (cadr rm)) (> (car rm) (cadr rr)) (> (car rr) (cadr ri))) (list rl rm rr ri))
(setq stt (bht:photo-stats) r (bht:photo-sync))
(tchk "B06" "ảnh: 205 JPG tìm thấy; đồng bộ lại không tạo trùng ký hiệu" (and (= (rv stt 'jpg-found) 205) (= (rv r 'created) 0) (= (t-mk-count) 203)) (list stt))
(setq k (bht:check))
(tchk "B07" "BHTKT sau mở lại: 0 lỗi" (= (car k) 0) (strcat (itoa (car k)) " lỗi, " (itoa (cadr k)) " cảnh báo"))
(foreach l (caddr k) (if (or (bht:starts l "LỖI") (bht:starts l "CẢNH BÁO")) (tlog (strcat "   KT: " l))))
(tend "B")
(princ)
