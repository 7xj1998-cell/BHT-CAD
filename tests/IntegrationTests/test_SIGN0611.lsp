(setq *sign0611-fail* 0)
(defun qa0611-check (name ok) (princ (strcat "\n" (if ok "PASS " "FAIL ") name)) (if (not ok) (setq *sign0611-fail* (1+ *sign0611-fail*))))
(load (strcat *bht-module-root* "/test_SIGN0610.lsp"))
(setq qa-h (bht:obj-read "OBJ-QA0610-H") qa-km (bht:obj-read "OBJ-QA0610-KM"))
(qa0611-check "station-from-Km-H" (= (bht:get qa-h "ly_trinh_km") "Km39+900.00"))
(qa0611-check "station-from-milestone" (= (bht:get qa-km "ly_trinh_km") "Km39+000.00"))
(bht:obj-write "OBJ-QA0610-H" (bht:set (bht:set qa-h "marker_km" "46") "marker_h" "1"))
(qa0611-check "edited-station-Km46-H1" (= (bht:get (bht:obj-read "OBJ-QA0610-H") "ly_trinh_km") "Km46+100.00"))
(bht:obj-write "OBJ-QA0610-H" qa-h)
(bht:obj-create "OBJ-QA0611-PLAIN" '(("nhom" . "COC_TIEU")) '("QA0610-PT") T)
(setq qa-oldlabel (bht:text "Cọc tiêu" '(100019.0 99996.0 0.0) 0.35 "BHT_NHAN"))
(entmod (append (entget qa-oldlabel) (list (bht:kh-xdata-txt "OBJ-QA0611-PLAIN" "TU_DONG" '(100019.0 99996.0 0.0)))))
(bht:kh-free-apply "OBJ-QA0611-PLAIN" '(100019.0 99996.0 0.0) (- (/ pi 2)) nil)
(bht:symbol-sync '("OBJ-QA0610-KM" "OBJ-QA0611-PLAIN"))
(qa0611-check "plain-marker-no-label" (null (assoc "OBJ-QA0611-PLAIN" (bht:tagged-pairs "TEXT" "BHT_KH" 1))))
(qa0611-check "old-owned-label-removed" (null (entget qa-oldlabel)))
(qa0611-check "milestone-no-external-label" (null (assoc "OBJ-QA0610-KM" (bht:tagged-pairs "TEXT" "BHT_KH" 1))))
(setq qa-bar nil qa-entity (tblobjname "BLOCK" "BHT_KH_COT_KM_V0611"))
(while (and (setq qa-entity (entnext qa-entity)) (/= (cdr (assoc 0 (entget qa-entity))) "ENDBLK"))
  (if (and (= (cdr (assoc 0 (entget qa-entity))) "SOLID") (= (cdr (assoc 62 (entget qa-entity))) 7)) (setq qa-bar (entget qa-entity))))
(qa0611-check "unnumbered-km-origin-at-bar-center" (and qa-bar (equal (/ (+ (car (cdr (assoc 10 qa-bar))) (car (cdr (assoc 11 qa-bar)))) 2.0) 0.0 1e-8)))
(qa0611-check "builtin-sign-face-follows-picked-up" (equal (bht:kh-picked-rotation '(("nhom" . "BIEN_BAO") ("custom_block" . "BHT_KH_BB_W201_V044")) '(0.0 0.0 0.0) '(0.0 1.0 0.0)) 0.0 1e-8))
(qa0611-check "custom-block-keeps-own-X-axis" (equal (bht:kh-picked-rotation '(("nhom" . "BIEN_BAO") ("custom_block" . "BHT_KH_BANG_QC")) '(0.0 0.0 0.0) '(0.0 1.0 0.0)) (/ pi 2.0) 1e-8))
(setq qa-before-point (entget qa0610-point))
(foreach dir '((0.0 1.0 0.0) (0.0 -1.0 0.0) (1.0 0.0 0.0) (-1.0 0.0 0.0))
  (setq qa-rot (bht:kh-picked-rotation qa-h '(0.0 0.0 0.0) dir))
  (qa0611-check "red-cap-matches-picked-direction" (equal (polar '(0.0 0.0 0.0) (+ qa-rot pi) 1.0) dir 1e-8)))
(qa0611-check "survey-point-still-unchanged" (equal qa-before-point (entget qa0610-point)))
(princ (strcat "\nSIGN0611-FAIL=" (itoa *sign0611-fail*)))
(princ)
