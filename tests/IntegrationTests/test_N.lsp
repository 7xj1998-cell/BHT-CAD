;;; BHT 0.6.55 - phien N: BAN SAO ban ve do BHT 0.3.3 tao (A_out.dwg cua bo kiem thu 0.3.3: 526 diem, 205 anh,
;;; ho so, ky hieu, nhan). Nap BHT-0.4.6.lsp + NETLOAD BHT.Bridge.dll: C# doc giong het Lisp, C# ghi -> Lisp thay,
;;; Lisp ghi -> C# thay, goi Lisp tu .NET (Application.Invoke), bo dieu phoi, bo nho dem. SAVEAS 2018 o cuoi.
(load (strcat (getenv "BHT_TEST_DIR") "/t_common.lsp"))
(tbegin "N")
(setq e (tload))
(tchk "N00" "nạp BHT-5.0 trên bản vẽ 0.3.3" (and (null e) (= *bht-version* "0.6.55")) (if e e (getvar "DWGNAME")))
(tchk "N01" "16 hàm API đăng ký vl-acad-defun (5.0 thêm bht:api-route-diag)" (= *bht-api-registered* 16) *bht-api-registered*)
(setq NP (length (bht:pt-all)) NPH (length (bht:rec-keys "PHOTO")) NO (length (bht:obj-ids))
      CK0 (bht:check) SNAP (t-snapshot) PC0 (t-pt-coords))
(tlog (strcat "   bản vẽ 0.3.3: điểm " (itoa NP) ", ảnh " (itoa NPH) ", hồ sơ " (itoa NO) ", BHTKT lỗi " (itoa (car CK0)) " cảnh báo " (itoa (cadr CK0))
              " | SECURELOAD=" (vl-princ-to-string (getvar "SECURELOAD"))))
(setq e (t-netload "BHT.Bridge.dll"))
(t-dump (t-run "N_L1.txt"))
(command "BHTNETDUMP" (t-run "N_C1.txt"))
(tchk "N02" "NETLOAD BHT.Bridge.dll (chỉ AcDbMgd/AcCoreMgd) trong Core Console; lệnh .NET chạy được" (and (null e) (findfile (t-run "N_C1.txt"))) e)
(setq cmp (t-cmp (t-run "N_L1.txt") (t-run "N_C1.txt")))
(tchk "N03" "C# đọc GIỐNG HỆT Lisp (dump từng dòng: điểm + chuỗi gốc + tọa độ, mọi bản ghi OBJ/PHOTO/DATASET/META/ROUTE/SEG, đường dẫn JPG)" (car cmp) cmp)
(tlog (strcat "   bản vẽ 0.3.3 (A_out): " (itoa NP) " điểm = 526 điểm thật + 60 điểm khu dày giả lập của phiên A 0.3.3"))
(tchk "N04" "C# đọc đủ số điểm RTK (= Lisp, ≥ 526 thật) và 205 bản ghi ảnh, số hồ sơ = Lisp"
      (and (= (t-count-prefix (t-run "N_C1.txt") "P|") NP) (>= NP 526) (= (t-count-prefix (t-run "N_C1.txt") "R|PHOTO|") 205 NPH)
           (= (t-count-prefix (t-run "N_C1.txt") "R|OBJ|") NO))
      (list (t-count-prefix (t-run "N_C1.txt") "P|") (t-count-prefix (t-run "N_C1.txt") "R|PHOTO|") (t-count-prefix (t-run "N_C1.txt") "R|OBJ|") NO))
(setq nj 0) (foreach l (t-lines (t-run "N_C1.txt")) (if (and (wcmatch l "J|*") (not (wcmatch l "J|*|"))) (setq nj (1+ nj))))
(tlog (strcat "   C# tìm thấy JPG cho " (itoa nj) "/" (itoa NPH) " ảnh (cùng kết quả với bht:photo-path, đã so trong N03)"))

;; --- C# tao ho so (tieng Viet) ---
(setq owners (bht:pt-owner-map) FREE nil)
(foreach it (bht:pt-all) (if (and (< (length FREE) 3) (not (assoc (car it) owners))) (setq FREE (append FREE (list (bht:pv (cdr it) 'id))))))
(setq P1 (car FREE) P2 (cadr FREE) P3 (caddr FREE) NID (bht:obj-next-id))
(command "BHTNETTAO" "." (strcat P1 "," P2) "2" "207a" "3" "tốt, nghiêng nhẹ" "tạo từ .NET – kiểm thử" "K")
(setq rec (bht:obj-read NID))
(tchk "N05" "C# tạo hồ sơ (tiếng Việt): Lisp đọc được; ID = bht:obj-next-id; nhóm/số trụ/tình trạng/ghi chú/điểm đúng; META obj_seq cập nhật"
      (and rec (= (bht:get rec "object_id") NID) (= (bht:get rec "nhom") "COC_TIEU") (= (bht:get rec "so_tru") "3")
           (= (bht:get rec "tinh_trang") "tốt, nghiêng nhẹ") (= (bht:get rec "ghi_chu") "tạo từ .NET – kiểm thử")
           (equal (bht:get-all rec "pt") (list (strcase P1) (strcase P2))) (= (bht:meta "obj_seq" "") (itoa (bht:obj-seq-num NID))))
      (list NID P1 P2 rec))
;; ban ghi doi chieu do Lisp tao (cung truong) -> so thu tu khoa + gia tri
(setq r (bht:obj-create "LISP-TWIN" (list (cons "nhom" "2") (cons "ma_hieu" "207a") (cons "so_tru" "3") (cons "tinh_trang" "tốt, nghiêng nhẹ")
                                          (cons "ghi_chu" "tạo từ .NET – kiểm thử")) (list P1 P2) T))
(setq tw (bht:obj-read "LISP-TWIN"))
(tchk "N06" "bản ghi C# có THỨ TỰ khóa và giá trị giống bản ghi do bht:obj-create (Lisp) tạo (trừ object_id/tao_luc/sua_luc)"
      (and (car r) (equal (mapcar 'car rec) (mapcar 'car tw))
           (equal (vl-remove-if '(lambda (p) (member (car p) '("object_id" "tao_luc" "sua_luc"))) rec)
                  (vl-remove-if '(lambda (p) (member (car p) '("object_id" "tao_luc" "sua_luc"))) tw)))
      (list (mapcar 'car rec) (mapcar 'car tw)))
(bht:obj-delete "LISP-TWIN")
(setq n0 (length (bht:obj-ids)))
(command "BHTNETTAO" "." P1 "2" "." "." "." "." "K")
(tchk "N07" "C# MẶC ĐỊNH từ chối tạo hồ sơ mới cho điểm đã thuộc hồ sơ khác (không tạo trùng)" (= (length (bht:obj-ids)) n0) (bht:obj-ids))
(setq NID2 (bht:obj-next-id))
(command "BHTNETTAO" "." P1 "2" "." "." "." "chung điểm" "C")
(tchk "N08" "C# chỉ tạo hồ sơ dùng chung điểm khi xác nhận rõ (C); Lisp thấy điểm thuộc 2 hồ sơ"
      (and (bht:obj-read NID2) (equal (cdr (assoc (strcase P1) (bht:pt-owner-map))) (list NID NID2))) (cdr (assoc (strcase P1) (bht:pt-owner-map))))
(bht:obj-delete NID2)
(setq t0 (bht:get (bht:obj-read NID) "sua_luc"))
(command "BHTNETSUA" NID "ghi_chu" "đã sửa từ C#")
(setq rec2 (bht:obj-read NID))
(tchk "N09" "C# sửa trường: Lisp thấy giá trị mới, các trường khác giữ nguyên, sua_luc có mặt"
      (and (= (bht:get rec2 "ghi_chu") "đã sửa từ C#") (= (bht:get rec2 "so_tru") "3") (= (length rec2) (length rec)) (/= (bht:get rec2 "sua_luc") ""))
      rec2)
(command "BHTNETTHEMDIEM" NID P3)
(tchk "N10" "C# thêm điểm: Lisp thấy 3 điểm theo thứ tự, không trùng" (equal (bht:get-all (bht:obj-read NID) "pt") (mapcar 'strcase (list P1 P2 P3))) (bht:get-all (bht:obj-read NID) "pt"))
(setq PH nil)
(foreach k (bht:rec-keys "PHOTO") (if (and (null PH) (null (bht:get-all (bht:photo-read k) "doi_tuong"))) (setq PH k)))
(command "BHTNETGANANH" PH NID)
(setq prec (bht:photo-read PH))
(tchk "N11" "C# gắn ảnh: 2 chiều (hồ sơ.anh = PH|DA_XAC_NHAN|THU_CONG, ảnh.doi_tuong, trạng thái DA_XAC_NHAN); Lisp photos-for-point thấy"
      (and (member (strcat PH "|DA_XAC_NHAN|THU_CONG") (bht:get-all (bht:obj-read NID) "anh")) (equal (bht:get-all prec "doi_tuong") (list NID))
           (= (bht:get prec "trang_thai") "DA_XAC_NHAN") (member PH (car (bht:photos-for-point P1))))
      (list PH prec))
;; Lisp bo gan -> C# phai thay
(bht:photo-unlink PH NID)
(bht:photo-link PH NID "THU_CONG")
(command "BHTNETBOANH" PH NID)
(setq prec (bht:photo-read PH))
(tchk "N12" "Lisp gắn lại -> C# bỏ gắn: Lisp thấy ảnh CHUA_GHEP, hồ sơ không còn ảnh" (and (null (bht:get-all prec "doi_tuong")) (= (bht:get prec "trang_thai") "CHUA_GHEP") (null (bht:get-all (bht:obj-read NID) "anh"))) prec)
(bht:photo-link PH NID "THU_CONG")
(t-dump (t-run "N_L2.txt"))
(command "BHTNETDUMP" (t-run "N_C2.txt"))
(setq cmp (t-cmp (t-run "N_L2.txt") (t-run "N_C2.txt")))
(tchk "N13" "sau các lần ghi xen kẽ C#/Lisp: dump C# và Lisp vẫn giống hệt" (car cmp) cmp)
(tchk "N14" "ghi an toàn: không còn bản sao lưu *__BHT_CU sót lại" (= (t-backups) 0) (t-backups))
;; bo dieu phoi + bo nho dem (lenh .NET goi tu Lisp)
(command "BHTNETDIEUPHOI" (t-run "N_disp.txt"))
(setq dl (t-lines (t-run "N_disp.txt")))
(tchk "N15" "bộ điều phối: khi đang có lệnh -> báo bận (CommandInProgress) và TỪ CHỐI ghi / chạy ngữ cảnh lệnh (không ghi gì)"
      (and (wcmatch (car dl) "busy=1|*BHTNETDIEUPHOI*") (wcmatch (cadr dl) "runwrite_ok=0|*") (wcmatch (nth 3 dl) "runctx_ok=0|*")) dl)
(tchk "N16" "Application.Invoke khi Lisp đang bận (lệnh .NET gọi từ (command)): báo LỖI, không coi là thành công" (wcmatch (nth 4 dl) "lisp_ok=0|*") (nth 4 dl))
(command "BHTNETCACHE" (t-run "N_cache.txt"))
(setq cl (bht:split (car (t-lines (t-run "N_cache.txt"))) "|"))
(tchk "N17" "bộ nhớ đệm điểm bị vô hiệu khi DB đổi (ObjectAppended/Erased): n, n, n+1, n"
      (and (= (atoi (nth 0 cl)) NP) (= (atoi (nth 1 cl)) NP) (= (atoi (nth 2 cl)) (1+ NP)) (= (atoi (nth 3 cl)) NP)) cl)
;; ham c: Lisp cung ten lenh .NET (kiem tra uu tien) - chay o dong script BHTNETPING
(defun c:BHTNETPING () (setvar "USERS5" "LISP") (princ))
(setvar "USERS5" "")

;; --- cac buoc goi tu dong script (Lisp ranh) ---
(defun t-n-prep-invoke ()
  (setvar "USERS1" NID) (setvar "USERS2" PH) (setvar "USERS3" P1)
  (princ))

(defun t-inv (f) (t-lines (t-run f)))
(defun t-n-check-invoke (/ v i s s2 p c d b pg lb inf)
  (setq v (t-inv "N_inv_version.txt"))
  (tchk "N20" "Application.Invoke từ lệnh .NET (Lisp rảnh, ngữ cảnh lệnh): bht:api-version = OK 5.0 1" (and (= (car v) "OK") (= (cadr v) "0.6.55") (= (caddr v) "1")) v)
  (setq i (t-inv "N_inv_info.txt") inf (bht:obj-info-lines NID))
  (tchk "N21" "thông tin hồ sơ qua API = đúng các dòng BHTINFO (bht:obj-info-lines) của Lisp" (and (= (car i) "OK") (equal (cdr i) inf)) (list (length i) (length inf)))
  (setq s (t-inv "N_inv_sym.txt") s2 (t-inv "N_inv_sym2.txt"))
  (tchk "N22" "ký hiệu qua API theo object_id: lần 1 tạo 1, lần 2 không tạo thêm (không trùng)"
        (and (= (car s) "OK") (member "created=1" s) (= (car s2) "OK") (member "created=0" s2) (= (length (vl-remove-if-not '(lambda (x) (= (car x) NID)) (bht:tagged-pairs "INSERT" "BHT_KH" 1))) 1))
        (list s s2))
  (setq p (t-inv "N_inv_path.txt"))
  (tchk "N23" "đường dẫn JPG qua API = bht:photo-path của Lisp = kết quả C#" (and (= (car p) "OK") (= (cadr p) (bht:str (bht:photo-path (bht:photo-read PH))))) p)
  (setq lb (t-inv "N_inv_lbl.txt"))
  (tchk "N24" "nhãn qua API cho 1 điểm (phạm vi danh sách ID): OK, có báo cáo chồng lấn" (and (= (car lb) "OK") (vl-some '(lambda (x) (wcmatch x "overlap=*")) lb)) lb)
  (setq c (t-inv "N_inv_check.txt"))
  (tchk "N25" "kiểm tra qua API: số lỗi = BHTKT gọi trực tiếp; C# ghi không làm phát sinh lỗi mới so với đầu phiên"
        (and (= (car c) "OK") (= (cadr c) (strcat "loi=" (itoa (car (bht:check))))) (<= (car (bht:check)) (car CK0))) (list (cadr c) (caddr c) "đầu phiên" (car CK0)))
  (setq d (t-inv "N_inv_dro.txt"))
  (tchk "N26" "thứ tự hiển thị qua API: AutoCAD từ chối lệnh DRAWORDER trong acedInvoke -> API báo LỖI rõ ràng, chỉ dẫn BHTTHUTUVE (không báo thành công giả)"
        (and (= (car d) "LOI") (vl-string-search "BHTTHUTUVE" (cadr d))) d)
  (setq se (t-sortents) g (bht:draworder-groups)
        rl (t-rank-range (cdr (assoc 'labels g)) se) rm (t-rank-range (cdr (assoc 'mid g)) se) ri (t-rank-range (cdr (assoc 'irt g)) se))
  (tchk "N26b" "đường lệnh palette dùng: lệnh BHTTHUTUVE (gõ ở dòng script) sắp đúng nhãn > ký hiệu/POINT > ảnh nền IRT"
        (and (car rl) (car rm) (cadr ri) (> (car rl) (cadr rm)) (> (car rm) (cadr ri))) (list 'nhan rl 'giua rm 'irt ri))
  (setq inf (t-inv "N_inv_iph.txt"))
  (tchk "N27" "thông tin ảnh qua API = bht:photo-info-lines" (and (= (car inf) "OK") (equal (cdr inf) (bht:photo-info-lines PH))) (length inf))
  (setq b (t-inv "N_inv_bad.txt"))
  (tchk "N28" "gọi hàm Lisp không tồn tại: C# báo LỖI (không coi là thành công)" (= (car b) "LOI") b)
  (setq pg (getvar "USERS5"))
  (tchk "N29" "gõ BHTPING: lệnh .NET được ưu tiên hơn hàm c: Lisp cùng tên" (= pg "NET") pg)
  (princ))

(defun t-n-final (/ cmp)
  (t-dump (t-run "N_L3.txt"))
  (command "BHTNETDUMP" (t-run "N_C3.txt"))
  (setq cmp (t-cmp (t-run "N_L3.txt") (t-run "N_C3.txt")))
  (tchk "N30" "cuối phiên (sau ký hiệu/nhãn/thứ tự qua API): dump C# = dump Lisp" (car cmp) cmp)
  (setq d (t-snap-diff SNAP))
  (tchk "N31" "thực thể KHÔNG phải BHT không bị đổi / xóa" (and (= (cadr d) 0) (= (caddr d) 0)) d)
  (tchk "N32" "không POINT RTK nào bị dời (tọa độ so với đầu phiên)" (equal (vl-sort PC0 '(lambda (a b) (< (car a) (car b)))) (vl-sort (t-pt-coords) '(lambda (a b) (< (car a) (car b))))) nil)
  (t-state-save "net_N" (list NID PH P1 P2 P3))
  (tend "N")
  (princ))
(princ)
