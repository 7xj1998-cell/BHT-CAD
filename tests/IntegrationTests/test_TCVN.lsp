(setq *tcvn-fail* 0)
(defun tcvn-check (name ok)
  (if (not ok) (setq *tcvn-fail* (1+ *tcvn-fail*)))
  (princ (strcat "\n" (if ok "PASS " "FAIL ") "TCVN " name)))
(tcvn-check "version-current" (= *bht-version* "0.6.55"))
(tcvn-check "find-real-font-path" (= (type (bht:sign-font-file)) 'STR))
(tcvn-check "vietnamese-mixed" (equal (vl-string->list (bht:tcvn-encode "Cọc tiêu")) '(67 228 99 32 116 105 170 117)))
(tcvn-check "decomposed-accent" (equal (bht:tcvn-encode (vl-list->string '(67 111 803 99 32 116 105 101 770 117))) (bht:tcvn-encode "Cọc tiêu")))
(tcvn-check "ASCII-unchanged" (= (bht:tcvn-encode "P.127-80 Km1+200") "P.127-80 Km1+200"))
(bht:meta-set "nhan_kieu_chu" "BHT_RTK")
(tcvn-check "old-default-migrates" (= (bht:default-label-style) "BHT_TCVN"))
;; Legacy BHT labels migrate before the shared style changes font.
(entmake '((0 . "STYLE") (100 . "AcDbSymbolTableRecord") (100 . "AcDbTextStyleTableRecord") (2 . "BHT_TCVN") (70 . 0) (40 . 0.0) (41 . 1.0) (50 . 0.0) (71 . 0) (42 . 1.0) (3 . "vnromanc.shx") (4 . "")))
(entmod (bht:dxf-put (entget (tblobjname "STYLE" "BHT_TCVN")) 3 "vnromanc.shx"))
(setq legacy (entmakex (list '(0 . "TEXT") '(10 10.0 10.0 0.0) '(40 . 0.5) '(7 . "BHT_TCVN") (cons 1 (bht:tcvn-encode "Ê ê")) '(50 . 0.4))))
(setq sty (bht:text-style (bht:default-label-style)))
(tcvn-check "default-Unicode-update" (and (= sty "BHT_TCVN") (= (cdr (assoc 3 (tblsearch "STYLE" sty))) "VNRomancUpdate.shx")))
(tcvn-check "legacy-E-migrates-correct-case" (= (cdr (assoc 1 (entget legacy))) "Ê ê"))
(tcvn-check "legacy-position-rotation-kept" (and (equal (cdr (assoc 10 (entget legacy))) '(10.0 10.0 0.0)) (equal (cdr (assoc 50 (entget legacy))) 0.4 1e-9)))
(tcvn-check "uppercase-distinct" (= (bht:cad-text "Ê ê Ế ế Ệ ệ" sty) "Ê ê Ế ế Ệ ệ"))
(tcvn-check "Unicode-NFD-composes-uppercase" (= (bht:cad-text (vl-list->string '(69 770 69 770 769)) sty) "ÊẾ"))
(entmake '((0 . "STYLE") (100 . "AcDbSymbolTableRecord") (100 . "AcDbTextStyleTableRecord") (2 . "CUSTOM_TCVN") (70 . 0) (40 . 0.0) (41 . 1.0) (50 . 0.0) (71 . 0) (42 . 1.0) (3 . "vnromanc.shx") (4 . "")))
(tcvn-check "custom-legacy-style-retains-TCVN" (= (bht:cad-text "Ê ê" "CUSTOM_TCVN") (bht:tcvn-encode "Ê ê")))
(setq direct (bht:text "Cọc tiêu" '(0.0 25.0 0.0) 0.5 "0"))
(tcvn-check "generic-text-Unicode" (and direct (= (cdr (assoc 7 (entget direct))) sty) (= (cdr (assoc 1 (entget direct))) "Cọc tiêu")))
(bht:regapp "BHT_ANHTEN")
(bht:layer "BHT_ANH_TEN" 4)
(setq photo (bht:photo-label-make "Ảnh" '(0.0 26.0 0.0) 0.5 sty))
(tcvn-check "photo-label-Unicode" (= (cdr (assoc 1 (entget photo))) "Ảnh"))
(bht:text-style "BHT_ARIAL")
(tcvn-check "Unicode-style-keeps-source" (= (bht:cad-text "Cọc tiêu" "BHT_ARIAL") "Cọc tiêu"))
(setq font-old *bht-sign-font* *bht-sign-font* "__BHT_MISSING_FONT__.shx")
(tcvn-check "missing-font-falls-back-Unicode" (= (bht:text-style "BHT_TCVN") "BHT_ARIAL"))
(setq *bht-sign-font* font-old)
(setq survey (entmakex '((0 . "POINT") (10 150.0 20.0 0.0))))
(bht:pt-write-xdata survey "TCVN-PT" "TCVN" "1" "Tên điểm" 20.0 150.0 0.0 "COC_TIEU" "test" "Cọc tiêu" "")
(setq source-before (bht:xget survey "BHT_PT"))
(bht:lbl-sync-scope '("TCVN-PT"))
(setq label (cadr (assoc "TCVN-PT|MOTA" (bht:group-pairs (bht:tagged-pairs "TEXT" "BHT_NHAN" 2)))))
(tcvn-check "survey-label-Unicode" (and label (= (cdr (assoc 1 (entget label))) "Cọc tiêu") (= (cdr (assoc 7 (entget label))) "BHT_TCVN")))
(setq prior (entget label))
(bht:lbl-sync-scope '("TCVN-PT"))
(tcvn-check "survey-repeat-idempotent" (equal prior (entget label)))
(setq manual-position '(155.0 35.0 0.0))
(entmod (bht:dxf-put (bht:dxf-put (bht:dxf-put (entget label) 1 "Cọc tiêu") 7 "BHT_ARIAL") 10 manual-position))
(bht:lbl-sync-scope '("TCVN-PT"))
(tcvn-check "old-label-converted-manual-position-kept" (and (= (cdr (assoc 1 (entget label))) "Cọc tiêu") (equal (cdr (assoc 10 (entget label))) manual-position)))
(tcvn-check "source-XData-Unicode-unchanged" (equal source-before (bht:xget survey "BHT_PT")))
(bht:obj-create "OBJ-TCVN" (list (cons "nhom" "COC_TIEU") (cons "mo_ta" "Cọc tiêu")) '("TCVN-PT") nil)
(bht:obj-write "OBJ-TCVN" (bht:set (bht:obj-read "OBJ-TCVN") "ly_trinh_km" "Km1+200.00"))
(bht:symbol-sync '("OBJ-TCVN"))
(setq kh (cadr (assoc "OBJ-TCVN" (bht:group-pairs (bht:tagged-pairs "TEXT" "BHT_KH" 1)))))
(tcvn-check "object-label-vnromanc-Unicode" (and kh (= (cdr (assoc 7 (entget kh))) "BHT_BIENBAO") (= (cdr (assoc 1 (entget kh))) "Cọc tiêu Km 1+200")))
(setq kh-before (entget kh))
(bht:symbol-sync '("OBJ-TCVN"))
(tcvn-check "object-repeat-idempotent" (equal kh-before (entget kh)))
(tcvn-check "valid-text-bounds" (and (listp (bht:lbl-tbox "Cọc tiêu" 0.5 sty)) (> (car (cadr (bht:lbl-tbox "Cọc tiêu" 0.5 sty))) 0.0)))
(setq upper-box (textbox (list '(0 . "TEXT") '(10 0.0 0.0 0.0) '(40 . 1.0) (cons 7 sty) '(1 . "Ê")))
      lower-box (textbox (list '(0 . "TEXT") '(10 0.0 0.0 0.0) '(40 . 1.0) (cons 7 sty) '(1 . "ê"))))
(tcvn-check "real-SHX-uppercase-glyph-taller" (> (- (cadr (cadr upper-box)) (cadr (car upper-box))) (- (cadr (cadr lower-box)) (cadr (car lower-box)))))

(setq tcvn-mismatch 0 nfc-mismatch 0)
(foreach pair *review-tcvn-expected*
  (if (/= (bht:tcvn-encode (car pair)) (chr (cdr pair))) (setq tcvn-mismatch (1+ tcvn-mismatch))))
(foreach pair *review-nfc-expected*
  (if (/= (bht:unicode-nfc (car pair)) (cdr pair)) (setq nfc-mismatch (1+ nfc-mismatch))))
(tcvn-check "all-266-legacy-inputs-equivalent" (= tcvn-mismatch 0))
(tcvn-check "all-178-NFC-inputs-equivalent" (= nfc-mismatch 0))
(tcvn-check "partial-compositions-keep-case" (= (bht:unicode-nfc (vl-list->string '(202 769 234 769 194 803 226 803))) "ẾếẬậ"))
(tcvn-check "noncanonical-Vietnamese-order" (= (bht:unicode-nfc (vl-list->string '(65 770 803 97 770 803))) "Ậậ"))
(tcvn-check "uppercase-seven-exceptions-kept" (equal (vl-string->list (bht:tcvn-encode "ĂÂÊÔƠƯĐ")) '(161 162 163 164 165 166 167)))
(princ (strcat "\nTCVN-TEST-FAIL=" (itoa *tcvn-fail*)))
(princ)

;; Migration must exercise both engines, not silently fall back to Lisp.
(if (bht:fn-defined-p 'BHTNATIVETEXT)
  (progn
    (setq *bht-force-lisp-text* nil)
    (bht:unicode-nfc "Ê")
    (tcvn-check "native-engine-active" (= *bht-text-backend* "NET"))
    (tcvn-check "native-legacy-decode-equivalent" (vl-every '(lambda (p) (= (bht:tcvn-decode (chr (cdr p))) (bht:legacy-tcvn-decode (chr (cdr p))))) *review-tcvn-expected*))
    (setq *bht-force-lisp-text* T)
    (tcvn-check "forced-lisp-equivalent" (vl-every '(lambda (p) (= (bht:tcvn-encode (car p)) (chr (cdr p)))) *review-tcvn-expected*))
    (setq *bht-force-lisp-text* nil)))
(princ (strcat "\nTCVN-TEST-FAIL=" (itoa *tcvn-fail*)))
