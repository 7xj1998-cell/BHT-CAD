(setq km-fails 0)
(defun km-check (n ok) (if (not ok) (setq km-fails (1+ km-fails))) (princ (strcat "\n" (if ok "PASS KM " "FAIL KM ") n)))
(setq km-before (bht:obj-read "HEAD-A") km-other (bht:obj-read "HEAD-B"))
(km-check "missing-controls-message-no-mutation" (and (= (car (bht:api-object-station "HEAD-A")) "LOI") (equal km-before (bht:obj-read "HEAD-A"))))
(bht:route-add-mark "HEAD-ROUTE" 0.0 45000.0 45000.0 "QA" "")
(bht:route-add-mark "HEAD-ROUTE" 20.0 45020.0 45020.0 "QA" "")
(km-check "selected-record-only-success" (and (= (car (bht:api-object-station "HEAD-A")) "OK") (/= (bht:get (bht:obj-read "HEAD-A") "ly_trinh_km") "") (equal km-other (bht:obj-read "HEAD-B"))))
(km-check "missing-object-message" (= (car (bht:api-object-station "MISSING")) "LOI"))
(setq km-before (bht:obj-read "HEAD-A"))
(foreach rid (bht:route-ids) (bht:rec-delete "ROUTE" rid))
(km-check "no-route-message-preserves-record" (and (= (car (bht:api-object-station "HEAD-A")) "LOI") (equal km-before (bht:obj-read "HEAD-A"))))
(setq kr (bht:km-two-marks '(0.0 0.0 12.0) 45000.0 '(100.0 0.0 99.0) 46000.0 '(25.0 10.0 80.0)))
(km-check "chord-interpolation-XY-offset" (and (car kr) (equal (cadr kr) 45250.0 1e-8) (equal (caddr kr) 10.0 1e-8)))
(km-check "reverse-order-invariant" (equal kr (bht:km-two-marks '(100.0 0.0) 46000.0 '(0.0 0.0) 45000.0 '(25.0 10.0)) 1e-8))
(km-check "coincident-rejected" (not (car (bht:km-two-marks '(0.0 0.0) 0.0 '(0.0 0.0) 1.0 '(0.0 0.0)))))
(km-check "same-station-rejected" (not (car (bht:km-two-marks '(0.0 0.0) 0.0 '(10.0 0.0) 0.0 '(5.0 0.0)))))
(km-check "outside-rejected" (not (car (bht:km-two-marks '(0.0 0.0) 0.0 '(10.0 0.0) 10.0 '(15.0 0.0)))))
(princ (strcat "\nKM-FAIL=" (itoa km-fails)))
