(defun support-end (e / d pts) (setq d (entget e)) (if (= (cdr (assoc 0 d)) "LINE") (cdr (assoc 11 d)) (append (cdr (last (vl-remove-if-not '(lambda (x) (= (car x) 10)) d))) (list (cdr (assoc 38 d))))))
(defun support-start (e / d) (setq d (entget e)) (if (= (cdr (assoc 0 d)) "LINE") (cdr (assoc 10 d)) (append (cdr (assoc 10 d)) (list (cdr (assoc 38 d))))))
(defun support-entities (name type / e out)
  (setq e (tblobjname "BLOCK" name) out nil)
  (while (and (setq e (entnext e)) (/= (cdr (assoc 0 (entget e))) "ENDBLK"))
    (if (= (cdr (assoc 0 (entget e))) type) (setq out (cons e out))))
  out)
(defun support-lines (id)
  (mapcar 'cdr (vl-remove-if-not '(lambda (pair) (and (= (car pair) id) (/= (nth 2 (bht:xget (cdr pair) "BHT_KH")) "@BHT_RAIL"))) (append (bht:tagged-pairs "LINE" "BHT_KH" 1) (bht:tagged-pairs "LWPOLYLINE" "BHT_KH" 1)))))
(defun support-lines-correct (id insert / feet line source end ok targets)
  (setq feet (BHTSIGNFEET (cdr (assoc 2 (entget insert)))) ok T)
  (setq targets (mapcar '(lambda (i) (bht:kh-foot-world (list (nth i feet) (nth (1+ i) feet) (nth (+ i 2) feet)) (list (cdr (assoc 10 (entget insert))) (cdr (assoc 41 (entget insert))) (cdr (assoc 50 (entget insert)))))) '(0 3)))
  (if (and (wcmatch (cdr (assoc 2 (entget insert))) "BHT_SUPPORT_V0645_2_*") (null (bht:kh-via-points (bht:obj-read id))))
    (setq targets (list (mapcar '(lambda (a b) (/ (+ a b) 2.0)) (car targets) (cadr targets)))))
  (foreach line (support-lines id)
    (setq source (bht:pt-find (nth 2 (bht:xget line "BHT_KH")) (bht:pt-all)) end (support-end line))
    (if (not (and source (equal (support-start line) (bht:pv source 'xyz) 1e-8) (vl-some '(lambda (pt) (equal pt end 1e-8)) targets))) (setq ok nil)))
  ok)
(setq support-first (entmakex '((0 . "POINT") (10 150.0 40.0 0.0))) support-second (entmakex '((0 . "POINT") (10 154.0 42.0 0.0))))
(bht:pt-write-xdata support-first "FOOT-1" "SUPPORT" "1" "Chân 1" 40.0 150.0 0.0 "BIEN_BAO" "test" "chân biển" "")
(bht:pt-write-xdata support-second "FOOT-2" "SUPPORT" "2" "Chân 2" 42.0 154.0 0.0 "BIEN_BAO" "test" "chân biển" "")
(setq support-RTK-before (list (entget support-first '("BHT_PT")) (entget support-second '("BHT_PT"))))
(bht:obj-create "OBJ-FOOT-BOARD" '(("nhom" . "KHAC") ("so_tru" . "2") ("mo_ta" . "Bảng thông báo quy mô")) '("FOOT-2" "FOOT-1") T)
(signs-check "support-board-place-success" (= (cdr (assoc 'created (bht:kh-free-apply "OBJ-FOOT-BOARD" '(160.0 50.0 0.0) 0.4 nil))) 1))
(setq support-insert (cdr (assoc "OBJ-FOOT-BOARD" (bht:tagged-pairs "INSERT" "BHT_KH" 1))) support-block (cdr (assoc 2 (entget support-insert))))
(signs-check "support-board-two-poles-two-feet" (and (= (length (support-entities support-block "LINE")) 2) (= (length (support-entities support-block "CIRCLE")) 2)))
(signs-check "support-two-measured-points-two-leaders" (= (length (support-lines "OBJ-FOOT-BOARD")) 2))
(setq support-two-lines (support-lines "OBJ-FOOT-BOARD"))
(signs-check "support-leaders-use-shared-midpoint" (equal (support-end (car support-two-lines)) (support-end (cadr support-two-lines)) 1e-8))
(signs-check "support-leaders-start-at-RTK-and-end-at-rotated-feet" (support-lines-correct "OBJ-FOOT-BOARD" support-insert))
(setq support-before (mapcar '(lambda (e) (entget e '("BHT_KH"))) (support-lines "OBJ-FOOT-BOARD")))
(bht:symbol-sync '("OBJ-FOOT-BOARD"))
(signs-check "support-refresh-no-duplicates-idempotent" (equal support-before (mapcar '(lambda (e) (entget e '("BHT_KH"))) (support-lines "OBJ-FOOT-BOARD"))))
(bht:kh-free-apply "OBJ-FOOT-BOARD" '(165.0 52.0 0.0) 2.8 nil)
(signs-check "support-move-rotate-reconnects-both-feet" (and (= (length (support-lines "OBJ-FOOT-BOARD")) 2) (support-lines-correct "OBJ-FOOT-BOARD" support-insert)))
(setq support-rec (bht:obj-read "OBJ-FOOT-BOARD"))
(bht:obj-write "OBJ-FOOT-BOARD" (bht:set-all support-rec "pt" '("FOOT-1")))
(bht:symbol-sync '("OBJ-FOOT-BOARD"))
(signs-check "support-remove-point-removes-only-its-leader" (and (= (length (support-lines "OBJ-FOOT-BOARD")) 1) (= (nth 2 (bht:xget (car (support-lines "OBJ-FOOT-BOARD")) "BHT_KH")) "FOOT-1")))
(signs-check "support-missing-measured-foot-warning" (vl-some '(lambda (line) (wcmatch line "*OBJ-FOOT-BOARD*điểm RTK đo chân*")) (caddr (bht:check))))
(bht:obj-write "OBJ-FOOT-BOARD" support-rec)
(bht:symbol-sync '("OBJ-FOOT-BOARD"))
(signs-check "support-add-point-restores-its-leader" (= (length (support-lines "OBJ-FOOT-BOARD")) 2))
(bht:obj-write "OBJ-FOOT-BOARD" (bht:set support-rec "so_tru" "1"))
(bht:symbol-sync '("OBJ-FOOT-BOARD"))
(setq support-one-block (cdr (assoc 2 (entget support-insert))))
(signs-check "support-count-two-to-one-cleans-second-pole-and-leader" (and (= (length (support-entities support-one-block "LINE")) 1) (= (length (support-entities support-one-block "CIRCLE")) 1) (= (length (support-lines "OBJ-FOOT-BOARD")) 1)))
(bht:obj-write "OBJ-FOOT-BOARD" (bht:set support-rec "so_tru" "0"))
(bht:symbol-sync '("OBJ-FOOT-BOARD"))
(signs-check "support-zero-count-removes-poles-and-feet" (and (null (support-entities (cdr (assoc 2 (entget support-insert))) "LINE")) (null (support-entities (cdr (assoc 2 (entget support-insert))) "CIRCLE"))))
(bht:obj-write "OBJ-FOOT-BOARD" support-rec)
(bht:kh-free-apply "OBJ-FOOT-BOARD" '(165.0 52.0 0.0) 0.4 '((157.0 47.0 0.0)))
(setq support-vias (mapcar 'cdr (vl-remove-if-not '(lambda (pair) (= (car pair) "OBJ-FOOT-BOARD")) (bht:tagged-pairs "LWPOLYLINE" "BHT_KH" 1))))
(signs-check "support-waypoints-two-paths" (and (= (length support-vias) 2) (vl-every '(lambda (e) (= (cdr (assoc 90 (entget e))) 3)) support-vias)))
(bht:obj-create "OBJ-FOOT-SIGN" '(("nhom" . "BIEN_BAO") ("so_tru" . "2") ("so_mat" . "2") ("ma_hieu" . "W.225") ("mat" . "W.225") ("mat" . "S.501@500")) '("FOOT-1" "FOOT-2") T)
(bht:kh-free-apply "OBJ-FOOT-SIGN" '(165.0 65.0 0.0) 0.7 nil)
(setq support-sign-insert (cdr (assoc "OBJ-FOOT-SIGN" (bht:tagged-pairs "INSERT" "BHT_KH" 1))) support-sign-block (cdr (assoc 2 (entget support-sign-insert))))
(signs-check "support-multi-face-two-poles-two-plates" (and (= (length (support-entities support-sign-block "CIRCLE")) 2) (= (length (support-entities support-sign-block "INSERT")) 2)))
(signs-check "support-multi-face-two-labels-two-leaders" (and (= (length (support-lines "OBJ-FOOT-SIGN")) 2) (= (length (cdr (assoc "OBJ-FOOT-SIGN" (bht:group-pairs (bht:tagged-pairs "TEXT" "BHT_KH" 1))))) 2)))
(bht:api-sign-scale "2" "0.75")
(signs-check "support-sign-scale-reconnects-both-feet" (support-lines-correct "OBJ-FOOT-SIGN" support-sign-insert))
(bht:api-sign-fill "0")
(signs-check "support-outline-keeps-two-feet-and-connections" (and (= (length (support-entities (cdr (assoc 2 (entget support-sign-insert))) "CIRCLE")) 2) (support-lines-correct "OBJ-FOOT-SIGN" support-sign-insert)))
(bht:api-sign-fill "1")
(bht:api-sign-scale "1" "1")
(signs-check "support-preserves-original-survey-entities-xdata" (equal support-RTK-before (list (entget support-first '("BHT_PT")) (entget support-second '("BHT_PT")))))
(setq support-custom (bht:kh-base-block '(("nhom" . "KHAC") ("so_tru" . "2") ("custom_block" . "SIGN_CUSTOM_TEST"))))
(signs-check "support-custom-block-preserved" (= support-custom "SIGN_CUSTOM_TEST"))
(bht:obj-delete "OBJ-FOOT-BOARD") (bht:obj-delete "OBJ-FOOT-SIGN")
(bht:symbol-sync nil)
(signs-check "support-delete-cleans-all-leaders" (and (null (support-lines "OBJ-FOOT-BOARD")) (null (support-lines "OBJ-FOOT-SIGN"))))
(princ (strcat "\nSIGN-TEST-FAIL=" (itoa *sign-test-fail*)))
(princ "\nSUPPORT-TEST-COMPLETED")
