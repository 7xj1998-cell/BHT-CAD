;;; Run on a drawing COPY with native TDT modules and BHT already loaded.
;;; Caller sets *qa-tdt-source*, *qa-tdt-count*, *qa-output*.
(setq qa-fail 0 qa-out (open *qa-output* "w" "utf8"))
(defun qa-check (name ok detail)
  (if (not ok) (setq qa-fail (1+ qa-fail)))
  (write-line (strcat (if ok "PASS " "FAIL ") name " | " (vl-princ-to-string detail)) qa-out))
(setq qa-source (handent *qa-tdt-source*) qa-before (entget qa-source '("*"))
      qa-ref (BHTTDT91ROUTE *qa-tdt-source* ""))
(qa-check "native-reference-created" (= (car qa-ref) "OK") qa-ref)
(setq qa-ref2 (BHTTDT91ROUTE *qa-tdt-source* (cadr qa-ref)))
(qa-check "same-reference-updated" (and (= (car qa-ref2) "OK") (= (cadr qa-ref) (cadr qa-ref2)) (= (nth 5 qa-ref2) "CAP_NHAT")) qa-ref2)
(setq qa-ent (handent (cadr qa-ref)))
(bht:route-create "QA-TDT-069" qa-ent "TIM_DUONG" 100.0 0.0 nil "Native TDT test on copy")
(setq qa-rec (bht:route-read "QA-TDT-069") qa-stakes (bht:tdt-stake-candidates qa-rec))
(qa-check "all-native-stakes" (and (/= (car qa-stakes) 'LOI) (= (length qa-stakes) *qa-tdt-count*)) (length qa-stakes))
(qa-check "stake-anchor-not-label-position"
  (vl-every '(lambda (c) (and (= (nth 5 c) "TDT_COC") (< (abs (- (cadr c) (nth 10 c))) 0.006) (< (nth 2 c) 0.02))) qa-stakes)
  (list (car qa-stakes) (last qa-stakes)))
(qa-check "repeat-scan-stable" (equal qa-stakes (bht:tdt-stake-candidates qa-rec)) (length qa-stakes))
(qa-check "scan-does-not-add-controls" (null (bht:route-marks (bht:route-read "QA-TDT-069"))) nil)
(setq qa-issues (bht:tdt-stake-issues qa-stakes))
(write-line (strcat "WARNINGS=" (itoa (length qa-issues))) qa-out)
(write-line (vl-princ-to-string qa-issues) qa-out)
(qa-check "source-unchanged" (equal qa-before (entget qa-source '("*"))) *qa-tdt-source*)

;; Inspect the drawing while the confirmation prompt is active, then REGEN.
(setq qa-saved-ask bht:ask-string qa-saved-route bht:ask-route qa-answer "K" qa-visible nil)
(defun bht:ask-route () "QA-TDT-069")
(defun bht:ask-string (prompt default / live)
  (setq live (ssget "_X" '((0 . "SOLID,LWPOLYLINE") (8 . "0") (62 . 2))))
  (vl-cmdf "_.REGEN")
  (setq qa-visible (and live (= (sslength live) 2)
                       (entget (ssname live 0)) (entget (ssname live 1))))
  qa-answer)
(setq qa-revision (bht:route-revision qa-rec))
(c:BHTROUTEREVERSE)
(qa-check "arrow-visible-during-prompt-and-regen" qa-visible nil)
(qa-check "cancel-keeps-direction" (= qa-revision (bht:route-revision (bht:route-read "QA-TDT-069"))) nil)
(qa-check "cancel-cleans-arrow" (null (ssget "_X" '((0 . "SOLID,LWPOLYLINE") (8 . "0") (62 . 2)))) nil)
(setq qa-answer "C")
(c:BHTROUTEREVERSE)
(qa-check "accept-saves-reverse" (= (bht:get (bht:route-read "QA-TDT-069") "direction") "-1") nil)
(qa-check "accept-cleans-arrow" (null (ssget "_X" '((0 . "SOLID,LWPOLYLINE") (8 . "0") (62 . 2)))) nil)
(setq bht:ask-string qa-saved-ask bht:ask-route qa-saved-route)

(vl-cmdf "_.UCS" "_Z" 37.0)
(foreach qa-dir '(1 -1)
  (foreach qa-dist (list 0.0 (bht:curve-length qa-ent))
    (setq qa-preview (bht:route-preview-direction qa-rec qa-dist qa-dir))
    (qa-check "endpoint-arrow-under-rotated-ucs" (= (length qa-preview) 2) (list qa-dist qa-dir))
    (bht:route-preview-clear qa-preview)))
(vl-cmdf "_.UCS" "_World")
(qa-check "source-unchanged-after-direction-tests" (equal qa-before (entget qa-source '("*"))) *qa-tdt-source*)
(setq qa-preview (bht:route-preview-direction qa-rec 0.0 1))
(bht:route-preview-clear qa-preview)
(bht:route-preview-clear qa-preview)
(qa-check "cleanup-is-idempotent" (vl-every '(lambda (e) (null (entget e))) qa-preview) nil)
(bht:route-set-start-dir "QA-TDT-069" (vlax-curve-getStartPoint qa-ent) 1)
(setq qa-add (bht:route-add-tdt-stakes "QA-TDT-069" qa-stakes qa-issues))
(qa-check "fixture-confirmation-skips-warnings" (= (car qa-add) (- *qa-tdt-count* (length qa-issues))) qa-add)
(setq qa-add2 (bht:route-add-tdt-stakes "QA-TDT-069" qa-stakes qa-issues))
(qa-check "repeat-confirmation-no-duplicates" (= (car qa-add2) 0) qa-add2)
(write-line (strcat "FAILURES=" (itoa qa-fail)) qa-out)
(close qa-out)
(princ)
